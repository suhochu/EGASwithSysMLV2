package RV_ActorModel {
    private import ReqCommon::*;
    private import ScalarValues::*;
    private import RV_InterfaceModel::*;

    @MetaInformation {
        version = "v0.2";
    }

    // ==========================================
    // 1. 내부 컴포넌트 정의 (Internal Components)
    // - 관심 시스템 내부의 요소로, 그레이박스 유스케이스(05번 파일)와 요구사항 할당(06번 파일)의 대상이 됨
    // ==========================================

    part def EngineControlUnit {
        // 시스템의 중앙 마이크로컨트롤러(µC)로서 가속 페달, 크루즈 컨트롤,
        // 외부 제어기의 토크 요구(Torque Request)를 수집 및 중재(Arbitration)함.
        // 목표 토크를 달성하기 위해 스로틀 밸브 및 연료/점화 시스템에 제어 명령을 내리며,
        //  오작동을 감지하는 안전 모니터링을 수행함.
        attribute confirmedFaultCause : FaultCause = FaultCause::NoFault; // 확정·래치된 치명 고장 원인 (고장 메모리. 영구 저장은 SYSR-09)
        attribute ccState : CruiseControlStateEnum = CruiseControlStateEnum::Off; // 크루즈 내부 상태 (요구/검증에서 참조)
        attribute ccSetSpeed :> ISQ::speed; // 기억된 설정 속도
        attribute dtcStorageTime :> ISQ::duration; // 고장 확정 ~ NVM 기록 완료 시간 관측값
        attribute commandGenerationTime :> ISQ::duration; // SYSR-08 바인딩용: 센서 값 수신 후 연료/점화 제어값 산출 단계 시간 관측값
        attribute lastAirMassFlow :> ISQ::massFlowRate; // 직전 제어 주기의 최종 공기량 명령 (이력 레지스터)
        attribute lastFuelPulseWidth :> ISQ::duration; // 직전 제어 주기의 최종 연료 분사 시간 명령
        attribute expectedAccessCredential : Integer; // [R3] 캘리브레이션 인가 기준 자격 (값은 모델 밖에서 관리)
        attribute storedDtcCode : Integer = 0; // [R2] 비휘발성 고장 메모리의 DTC (0: 없음). UF5_4가 기록
        attribute activeInterventionSource : InterventionSourceEnum; // 활성 개입의 송신원 (FE Out_ActiveSource에 바인딩)

        @MetaInformation { version = "v0.5"; }
    }

    part def AccelerationPedal {
        // 운전자의 물리적인 가속 의지(페달을 밟는 정도)를 전기적 신호로 변환하여 ECU에 1차적인 운전자 토크 요구량으로 전달함.
        item pedalPosition : AccelerationPedalPosition; // PVS1/PVS2 (내부 신호: 페달 → ECU)

        @MetaInformation {
            version = "v0.3";
        }
    }

    part def ThrottleValve {
        // ECU의 제어 명령에 따라 개방 각도를 조절하여 엔진으로 유입되는 공기량을 물리적으로 제어함.
        // 동시에 현재 밸브의 위치 값을 ECU로 피드백하여 정밀한 폐루프 제어(Closed-loop control)를 가능하게 함.

        // EGAS 내부 스로틀 루프 신호 (ECU ↔ ThrottleValve). 경계 포트가 아니라 요구/검증에서 참조하기 위한 내부 특성.
        item positionCommand : ThrottlePositionCommand; // ECU → 밸브 목표 개도
        item positionFeedback : ThrottlePositionFeedback; // 밸브 → ECU 실제 개도(TPS)
        attribute deviationDuration :> ISQ::duration; // 목표-실제 개도 편차 초과 지속시간 (ECU 모니터가 산출하는 관측값)

        @MetaInformation { version = "v0.3"; }
    }

    // ==========================================
    // 2. 외부 액터 정의 (External Actors)
    // ==========================================

    part def DriverActor {
        // 가속 페달을 밟아 가속 의도를 표현하는 물리적 운전자. AccelerationPedal(센서)이 EgasSystem
        // 내부 컴포넌트로 포함되므로, 운전자의 물리적 가속 의도가 시스템 경계를 넘는 입력이 된다.
        // (03번 파일의 stakeholder Driver와는 별개 개념: 이해관계자 관점이 아닌 컨텍스트 경계 관점의 액터)

        port driverPort : ~AccelerationInputPort;
        event occurrence pressesAccelPedal; // 가속 페달 입력 (가속 의지)

        @MetaInformation {
            version = "v0.3";
        }
    }

    part def CruiseControlLever {
        // 크루즈 컨트롤(Cruise Control) 활성화를 위한 운전자의 조작 상태를 전달하며,
        // 지정된 속도를 유지하기 위한 지속적인 토크 요구 명령을 시스템에 입력함.

        port ccPort : ~CruiseControlPort;
        event occurrence setsCruiseSpeed; // 크루즈 컨트롤 목표 속도 설정

        @MetaInformation {
            version = "v0.3";
        }
    }

    part def Brake {
        // 운전자의 제동 의지를 ECU에 전달함.
        // 가속 페달 신호와 브레이크 신호가 동시에 입력될 경우,
        // 제동을 우선시하여 토크를 강제로 차단하거나 줄이는 안전 기능(Brake Override)을 트리거함.

        port brakePort : ~BrakeInputPort;
        event occurrence pressesBrakePedal; // 브레이크 페달 입력 (제동 의지)

        @MetaInformation {
            version = "v0.3";
        }
    }

    part def AddEcu {
        // 변속기 제어기(TCU), 차체 자세 제어기(ESP) 등 다른 시스템의 마이크로컨트롤러가
        // 전송하는 토크 개입(Torque Intervention) 신호를 전달함.
        // 기어 변속 시점의 토크 저감이나 미끄럼 방지를 위한 토크 제한 등을 요구함.

        port addEcuPort : ~TorqueInterventionPort;
        event occurrence requestsIntervention; // 토크 개입 요청 (정상/지연/고착/해제 통합)

        @MetaInformation {
            version = "v0.3";
        }
    }

    part def AddSensorComponents {
        // 차량의 종방향 가속도 변화율(Jerk),엔진 회전수(RPM), 냉각수 온도, 흡기 온도 등 ECU가 목표 토크를
        // 정확하게 계산하고 보정하는 데 필요한 주변 환경 및 물리적 상태 데이터를 제공함.

        port sensorPort : ~SensorInputPort;
        event occurrence sendsNormalSensorData; // 정상 범위의 센서 데이터 송신
        event occurrence sendsFaultyData; // 물리적 결함(온도 초과 등) 데이터 송신
        event occurrence sendsDynamicsFeedback; // 차량 거동(Jerk 등) 피드백 송신

        @MetaInformation {
            version = "v0.3";
        }
    }

    part def FuelInjectionIgnitionSystem {
        // 스로틀 밸브의 공기량 제어와 협조하여,
        // ECU가 요구하는 최종 토크를 실제 엔진 동력으로 구현하기 위해 연료 분사량과 점화 시기를 제어하는 외부 구동계 역할을 수행함.

        port cmdPort : ~FuelCommandPort;
        port statusPort : ~CombustionStatusPort;

        event occurrence injectsFuel; // 연료/점화 제어 실행
        event occurrence executesReducedFuel; // 축소된 연료/점화 지각 실행
        event occurrence executesMaintainedFuel; // 동결(유지)된 연료량 실행
        event occurrence executesDriverBasedFuel; // 개입 해제 후 운전자 요구 기반 연료/점화 실행

        event occurrence executesFuelCut; // 연료 차단 실행 (제동 오버라이드 및 페일세이프 통합)
        event occurrence executesCompensatedFuel; // 보정된 연료/점화 제어 실행
        event occurrence sendsCombustionFeedback; // 연소 상태(실화율) 피드백 송신

        @MetaInformation {
            version = "v0.3";
        }
    }

    part def Engine {
        // 스로틀 밸브(ThrottleValve)를 통해 유입된 공기를 받아들이는 물리적 엔진 블록(실린더/흡기 매니폴드).
        // FuelInjectionIgnitionSystem과는 별도의 외부 액터로, 공기 경로(air path)만을 담당함.

        port intakePort : ~AirIntakePort;
        event occurrence receivesAirFlow; // 공기 유입 수용
        event occurrence receivesAirCut; // 공기 차단 수용
        event occurrence receivesReducedAir; // 축소된 공기량 수신
        event occurrence receivesMaintainedAir; // 동결(유지)된 공기량 수신
        event occurrence receivesDriverBasedAir; // 개입 해제 후 운전자 요구 기반 공기량 수신
        event occurrence receivesCompensatedAir; // 보정된 공기량 수신

        @MetaInformation {
            version = "v0.3";
        }
    }

    part def CalibrationTool {
        // 엔지니어가 사용하는 외부 XCP/CCP 튜닝 장비
        port calPort : ~CalibrationPort;
        event occurrence requestsValidAccess; // 유효한 메모리 주소 접근 요청
        event occurrence receivesAuthOk; // 인가 응답(200) 수신
        event occurrence sendsTuningData; // 튜닝 파라미터 데이터 송신
        event occurrence receivesVerifiedChecksum; // 검증된 체크섬 수신
        event occurrence requestsInvalidAccess; // 비유효/잘못된 메모리 주소 접근 요청
        event occurrence receivesErrorResponse; // 거절/에러 응답 수신

        @MetaInformation {
            version = "v0.3";
        }
    }

    part def DiagnosticTool {
        // 서비스 센터(A/S) 엔지니어가 사용하는 외부 진단 장비
        port diagPort : ~DiagnosticPort;
        event occurrence requestsDtcRead; // DTC 읽기(serviceId=1) 요청
        event occurrence receivesDtcResponse; // DTC 코드 및 200 응답 수신
        event occurrence requestsZeroPointCal; // 영점 조정(serviceId=2) 요청
        event occurrence receivesZeroPointResponse; // 영점 조정 완료(200) 응답 수신
        event occurrence requestsInvalidService; // 비유효 진단 서비스 요청
        event occurrence receivesErrorResponse; // 에러 응답 수신

        @MetaInformation {
            version = "v0.3";
        }
    }

    part def VehiclePowerSystem {
        // [신규 액터] 차량의 전원 배터리 및 시동 키/버튼 상태를 관리하는 외부 시스템
        port ignitionPort : ~IgnitionPort;

        event occurrence turnsIgnitionOn;
        event occurrence turnsIgnitionOff;
        @MetaInformation {
            version = "v0.1";
        }
    }

    part def DashboardHMI {
        // [신규 액터] 운전자에게 시각적/청각적 피드백을 제공하는 차량 계기판 및 클러스터
        port dashboardPort : ~DashboardPort;

        event occurrence displaysCriticalWarning;
        @MetaInformation {
            version = "v0.1";
        }
    }
} // package RV_ActorModel
