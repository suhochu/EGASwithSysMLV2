package RV_UseCases {
    private import RV_ContextModel::*;
    private import RV_StakeholderRequirementModel::*;
    private import ReqCommon::*;
    private import SI::*;
    private import RV_SystemRequirementsModel::Functional_Requirements::*;
    private import RV_SystemRequirementsModel::Performance_Requirements::*;
    private import RV_SystemRequirementsModel
            ::Diagnostics_Maintainability_Security_Architecture_Requirements::*;
    private import TimingConceptsAndLimits::*;

    constraint validationCriteria;

    use case def <UC1> 'Driving Torque Demand Arbitration & Control' {
        @MetaInformation {
            version = "v0.2";
        }

        doc
        /* Arbitrates driver/CC torque demands (incl. Brake Override), 
         * outputs engine/fuel commands, and receives feedback.
         */

        subject egas : EgasSystem;

        // Input actors
        actor driver : DriverActor;
        actor ccLever : CruiseControlLever;
        actor brake : Brake;
        actor powerSys : VehiclePowerSystem; // 점화 상태 입력
        actor addEcu : AddEcu;

        // Output/Feedback actors
        actor fuelSys : FuelInjectionIgnitionSystem;
        actor engine : Engine;
        actor dynamicsSensor : AddSensorComponents;

        satisfy requirement 'SHR-01'; // reqSafeTorqueArbitration
        satisfy requirement 'SHR-08'; // reqDriverPedalResponsiveness
        satisfy requirement 'SHR-02-1'; // reqSteadyStatePrecision
        satisfy requirement 'SYSR-01a';
        satisfy requirement 'SYSR-01b';
        satisfy requirement 'SYSR-08';
        satisfy requirement 'SYSR-10';
        satisfy requirement 'SYSR-13';
        satisfy requirement 'SYSR-18';
        satisfy requirement 'SYSR-20';
        satisfy requirement 'SYSR-23';
        satisfy requirement 'SYSR-24'; // reqIgnitionStateOperation
        satisfy requirement 'SYSR-26';
        // === Action Scenarios ===

        action UC1_Normal_Manual_Acceleration {
            doc
            /* [Main] Processes pedal input < 50ms, calculates torque, 
             * and commands engine/fuel for smooth acceleration (Jerk/Overshoot controlled).
             */

            constraint precondition {
                doc
                /* 운전자가 가속 페달을 밟았고 제동 오버라이드 트리거가 아닌 상태 (Exception과 배타). 크루즈는 SYSR-23에 따라 Active가 아님 */
                egas.accelPort.accelIntent.pedalDisplacement > 0.0 [mm] and
                not SafeStateLogic::IsBrakeOverrideTriggered(
                    egas.accelPort.accelIntent.pedalDisplacement,
                    egas.ecu.ccState,
                    egas.brakePort.brakeInput.pressure
                )
            }

            // Messages
            message msgAccel of AccelerationIntent
                from driver.pressesAccelPedal to egas.commandsManualTorque {
                bind payload = egas.accelPort.accelIntent;
            }

            message msgAirCmd of IntakeAirFlow
                from egas.commandsManualTorque to engine.receivesAirFlow {
                bind payload = egas.airIntakePort.airFlow;
                ref constraint <uc1_vc01>;
            }

            message msgFuelCmd of FuelIgnitionCommand
                from egas.commandsManualTorque to fuelSys.injectsFuel {
                bind payload = egas.fuelCmdPort.fuelCmd;
                ref constraint <uc1_vc01>;
            }

            // Feedback & non-functional constraints
            message msgFeedback of CombustionSystemStatus
                from fuelSys.injectsFuel to egas.commandsManualTorque {
                bind payload = egas.combustionStatusPort.combustionStatus;
                ref constraint <uc1_vc02>;
            }

            message msgDynamics of VehicleDynamicsFeedback
                from dynamicsSensor.sendsDynamicsFeedback to egas.commandsManualTorque {
                bind payload = egas.sensorPort.dynamicsStatus;
                ref constraint <uc1_vc03>;
            }

            // Sequence Flow
            first msgAccel;

            // Output air/fuel commands in parallel
            then fork commandOut;
                then msgAirCmd;
                then msgFuelCmd;

                    first msgAirCmd then j;
                    first msgFuelCmd then j;

            // Receive combustion and dynamics feedback in parallel
            join j;
            then fork feedbackIn;
                then msgFeedback;
                then msgDynamics;

            // Verification Criterias
            constraint <uc1_vc01> responseTimeConstraint :> validationCriteria {
                doc
                /* Response: Air/fuel command starts within 50ms of accel input. */
                msgAirCmd.start - msgAccel.done <= pedalResponseBudget and
                msgFuelCmd.start - msgAccel.done <= pedalResponseBudget
            }

            constraint <uc1_vc02> torqueOvershootConstraint :> validationCriteria {
                doc
                /* Precision: Torque overshoot <= 5.0%. */
                @PlantObservation;
                msgFeedback.payload.torqueOvershoot <= torqueOvershootLimitPct
            }

            constraint <uc1_vc03> rideComfortJerkConstraint :> validationCriteria {
                doc
                /* [uc1_vc03] 승차감: 정상 주행에서 종방향 Jerk가 한계 이내여야 함. 안전 개입 중에는 면제 (SHR-08 예외 조항, SYSR-26) */
                @PlantObservation;
                SafeStateLogic::IsNormalDriving(
                    egas.accelPort.accelIntent.pedalDisplacement,
                    egas.ecu.ccState,
                    egas.brakePort.brakeInput.pressure,
                    egas.ecu.confirmedFaultCause,
                    egas.torqueInterventionPort.torqueReq.requestedTorqueDelta
                ) implies
                msgDynamics.payload.longitudinalJerk <= longitudinalJerkLimit
            }

            constraint postcondition {
                doc
                /* Commands applied; overshoot and jerk within limits. 단, 승차감 항은 정상 주행에서만 적용 */
                @PlantObservation;
                msgFeedback.payload.torqueOvershoot <= torqueOvershootLimitPct and
                (SafeStateLogic::IsNormalDriving(
                        egas.accelPort.accelIntent.pedalDisplacement,
                        egas.ecu.ccState,
                        egas.brakePort.brakeInput.pressure,
                        egas.ecu.confirmedFaultCause,
                        egas.torqueInterventionPort.torqueReq.requestedTorqueDelta
                    ) implies
                    msgDynamics.payload.longitudinalJerk <= longitudinalJerkLimit)
            }
        }

        action UC1_Alternative_Cruise_Control_Driving {
            /* [Alt] CC calculates speed error and automatically commands 
             * torque via closed-loop control to maintain set speed.
             */
            constraint precondition {
                doc
                /* 크루즈가 활성(Active)이고 유효한 설정 속도가 있으며, 가속 페달과 제동이 없는 상태여야 함 (Normal, Exception과 배타) */
                egas.ecu.ccState == CruiseControlStateEnum::Active and
                egas.ecu.ccSetSpeed > 0.0 [km / h] and
                egas.accelPort.accelIntent.pedalDisplacement == 0.0 [mm] and
                egas.brakePort.brakeInput.pressure == 0.0 [Pa]
            }

            // Messages
            message msgCcReq of CruiseControlCommand
                from ccLever.setsCruiseSpeed to egas.commandsCruiseTorque {
                bind payload = egas.ccPort.ccCmd;
            }

            message msgAirCmd_CC of IntakeAirFlow
                from egas.commandsCruiseTorque to engine.receivesAirFlow {
                bind payload = egas.airIntakePort.airFlow;
            }

            message msgFuelCmd_CC of FuelIgnitionCommand
                from egas.commandsCruiseTorque to fuelSys.injectsFuel {
                bind payload = egas.fuelCmdPort.fuelCmd;
            }

            message msgFeedback_CC of CombustionSystemStatus
                from fuelSys.injectsFuel to egas.commandsCruiseTorque {
                bind payload = egas.combustionStatusPort.combustionStatus;
            }

            message msgDynamics_CC
                of VehicleDynamicsFeedback // 속도 폐루프 피드백
                from dynamicsSensor.sendsDynamicsFeedback to egas.commandsCruiseTorque {
                bind payload = egas.sensorPort.dynamicsStatus;
                ref constraint <uc1_vc04>;
            }

            // Sequence Flow
            first msgCcReq;

            fork commandOut;
                then msgAirCmd_CC;
                then msgFuelCmd_CC;

                    first msgAirCmd_CC then j;
                    first msgFuelCmd_CC then j;

            join j;
            then msgFeedback_CC;
            then msgDynamics_CC;

            // [Verification Criterias
            constraint <uc1_vc04> steadyStateErrorConstraint :> validationCriteria {
                /* [VC#04] 정밀도: 설정 속도와 실제 차속 간 정상 상태 속도 오차율이 한계(2.0%) 이내로 유지되어야 함 */
                @PlantObservation;
                CruiseControlLogic::IsCruiseSpeedHeld(
                    msgCcReq.payload.setSpeed,
                    msgDynamics_CC.payload.vehicleSpeed,
                    CruiseControlLogic::cruiseSpeedErrorLimitPct
                )
            }

            constraint postcondition {
                doc
                /* 시나리오 종료 시점에는 속도 오차가 한계 이내로 수렴되어 목표 속도가 안정적으로 유지된 상태여야 함 */
                CruiseControlLogic::IsCruiseSpeedHeld(
                    msgCcReq.payload.setSpeed,
                    msgDynamics_CC.payload.vehicleSpeed,
                    CruiseControlLogic::cruiseSpeedErrorLimitPct
                )
            }
        }

        action UC1_Alternative_Accel_Overrides_Cruise {
            doc
            /* [대안 시나리오]
             * 크루즈가 활성(Active)인 상태에서 운전자가 가속 페달을 밟으면 크루즈는 Suspended가 되고 설정 속도는 기억되며,
             * 운전자의 가속 요구가 공기/연료 명령을 결정하는 흐름 (SYSR-23)
             */

            constraint precondition {
                doc
                /* 크루즈가 활성이며 제동이 없는 상태에서 가속 페달 입력이 발생함 */
                egas.ecu.ccState == CruiseControlStateEnum::Active and
                egas.brakePort.brakeInput.pressure == 0.0 [Pa]
            }

            message msgAccel of AccelerationIntent
                from driver.pressesAccelPedal to egas.commandsManualTorque {
                bind payload = egas.accelPort.accelIntent;
            }
            message msgAirCmd of IntakeAirFlow
                from egas.commandsManualTorque to engine.receivesAirFlow {
                bind payload = egas.airIntakePort.airFlow;
                ref constraint <uc1_vc09>;
            }

            first msgAccel then msgAirCmd;

            constraint <uc1_vc09> cruiseSuspendedByPedal :> validationCriteria {
                doc
                /* [uc1_vc09] 가속 페달 입력 후 크루즈는 Suspended이고 설정 속도는 기억되어야 하며, 가속 요구에 대한 응답은 pedalResponseBudget 이내여야 함 */
                egas.ecu.ccState == CruiseControlStateEnum::Suspended and
                egas.ecu.ccSetSpeed > 0.0 [km / h] and
                msgAirCmd.start - msgAccel.done <= pedalResponseBudget
            }

            constraint postcondition {
                doc
                /* 크루즈가 일시 중단되고 설정 속도가 기억된 상태 (Resume 가능) */
                egas.ecu.ccState == CruiseControlStateEnum::Suspended and
                egas.ecu.ccSetSpeed > 0.0 [km / h]
            }
        }

        action UC1_Exception_Brake_During_Intervention {
            doc
            /* [예외 시나리오]
             * 외부 제어기(ESP/TCU)의 토크 저감 개입이 진행 중일 때 운전자가 가속과 제동을 동시에 입력하면,
             * 중재 결과와 무관하게 오버라이드가 유지되어 최종 출력이 L1 이내로 제한되는 흐름 (SYSR-01a, SYSR-18)
             */

            constraint precondition {
                doc
                /* 개입 요청(delta < 0)이 활성이고 구동 요구 중 제동 오버라이드 트리거가 성립한 상태 */
                egas.torqueInterventionPort.torqueReq.requestedTorqueDelta < 0.0 [N * m] and
                SafeStateLogic::IsBrakeOverrideTriggered(
                    egas.accelPort.accelIntent.pedalDisplacement,
                    egas.ecu.ccState,
                    egas.brakePort.brakeInput.pressure
                )
            }

            message msgInterventionReq of TorqueInterventionRequest
                from addEcu.requestsIntervention to egas.commandsEmergencyReduction {
                bind payload = egas.torqueInterventionPort.torqueReq;
            }
            message msgBrakeInput of BrakePedalPosition
                from brake.pressesBrakePedal to egas.overridesAndCutsTorque {
                bind payload = egas.brakePort.brakeInput;
            }
            message msgAirCutCmd of IntakeAirFlow
                from egas.overridesAndCutsTorque to engine.receivesAirCut {
                bind payload = egas.airIntakePort.airFlow;
                ref constraint <uc1_vc10>;
            }
            message msgFuelCutCmd of FuelIgnitionCommand
                from egas.overridesAndCutsTorque to fuelSys.executesFuelCut {
                bind payload = egas.fuelCmdPort.fuelCmd;
                ref constraint <uc1_vc10>;
            }

            first msgInterventionReq;
            then msgBrakeInput;
            fork commandOut;
                then msgAirCutCmd;
                then msgFuelCutCmd;

            constraint <uc1_vc10> overrideUnderIntervention :> validationCriteria {
                doc
                /* [uc1_vc10] 개입 중에도 제동 오버라이드 출력은 L1 이내이며 overrideResponseBudget 이내에 출력되어야 함 */
                SafeStateLogic::IsTorqueLimited(
                    msgAirCutCmd.payload.massFlow,
                    msgFuelCutCmd.payload.injectionPulseWidth
                ) and
                msgAirCutCmd.start - msgBrakeInput.done <= overrideResponseBudget and
                msgFuelCutCmd.start - msgBrakeInput.done <= overrideResponseBudget
            }

            constraint postcondition {
                doc
                /* 개입 중 제동이 입력되어도 최종 공기/연료가 L1 이내로 제한된 상태 */
                SafeStateLogic::IsTorqueLimited(
                    msgAirCutCmd.payload.massFlow,
                    msgFuelCutCmd.payload.injectionPulseWidth
                )
            }
        }

        action UC1_Alternative_Ignition_Off_Reset {
            doc
            /* [대안 시나리오]
             * 점화가 OFF되면 EGAS는 크루즈, 긴급 개입, 고장 래치를 모두 초기화하여 다음 시동에서 정상 상태로 시작하는 흐름 (SYSR-24)
             */

            constraint precondition {
                doc
                /* 점화 OFF가 수신된 상태여야 함 */
                egas.ignitionPort.ignitionStatus.status == IgnitionStatusEnum::Off
            }

            message msgIgnitionOff of IgnitionState
                from powerSys.turnsIgnitionOff to egas.resetsOnIgnitionOff {
                bind payload = egas.ignitionPort.ignitionStatus;
                ref constraint <uc1_vc08>;
            }

            first msgIgnitionOff;

            constraint <uc1_vc08> ignitionOffReset :> validationCriteria {
                doc
                /* 점화 OFF 처리 후 크루즈와 고장 래치가 초기 상태여야 함 (SYSR-19/21/23의 점화 OFF 결과) */
                egas.ecu.ccState == CruiseControlStateEnum::Off and
                egas.ecu.confirmedFaultCause == FaultCause::NoFault
            }

            constraint postcondition {
                doc
                /* 다음 시동은 크루즈 Off, 고장 래치 없음으로 시작해야 함 */
                egas.ecu.ccState == CruiseControlStateEnum::Off and
                egas.ecu.confirmedFaultCause == FaultCause::NoFault
            }
        }

        action UC1_Exception_Brake_Override_Intervention {
            doc
            /* [예외 시나리오]
             * 수동 가속 또는 크루즈 컨트롤 주행 중 운전자가 브레이크를 밟을 경우, 진행 중인 가속 요구를 즉각 무효화하고
             * 제동을 최우선으로 하여 공기/연료를 공회전 수준 이하(L1)로 제한하는 안전 개입 흐름
             * 제동이 먼저 입력된 상태에서 가속이 입력되는 경우를 포함한다
             */

            private import SafeStateLogic::*;
            constraint precondition {
                doc
                /* 구동 요구(가속 또는 크루즈)가 활성인 상태에서 브레이크 조작이 감지된 상태여야 함 (IsBrakeOverrideTriggered) */
                IsBrakeOverrideTriggered(
                    egas.accelPort.accelIntent.pedalDisplacement,
                    egas.ecu.ccState,
                    egas.brakePort.brakeInput.pressure
                )
            }

            // Messages
            message msgBrakeInput of BrakePedalPosition
                from brake.pressesBrakePedal to egas.overridesAndCutsTorque {
                bind payload = egas.brakePort.brakeInput;
            }

            message msgAirCutCmd of IntakeAirFlow
                from egas.overridesAndCutsTorque to engine.receivesAirCut {
                bind payload = egas.airIntakePort.airFlow;
                ref constraint <uc1_vc05>;
                ref constraint <uc1_vc06>;
            }

            message msgFuelCutCmd of FuelIgnitionCommand
                from egas.overridesAndCutsTorque to fuelSys.executesFuelCut {
                bind payload = egas.fuelCmdPort.fuelCmd;
                ref constraint <uc1_vc05>;
                ref constraint <uc1_vc07>;
            }

            // Sequence Flow
            first msgBrakeInput;
            fork commandOut;
                then msgAirCutCmd;
                then msgFuelCutCmd;

            // Verification Criterias
            constraint <uc1_vc05> overrideResponseTimeConstraint :> validationCriteria {
                doc
                /* Response: Override and issue cut-off commands within 10ms of brake input. */
                msgAirCutCmd.start - msgBrakeInput.done <= overrideResponseBudget and
                msgFuelCutCmd.start - msgBrakeInput.done <= overrideResponseBudget
            }

            constraint <uc1_vc06> airLimitFailSafe :> validationCriteria {
                doc
                /* [VC#06] 페일세이프: 스로틀 공기 유입을 공회전 수준 이하로 제한(L1) */
                msgAirCutCmd.payload.massFlow <= idleAirMassFlow
            }

            constraint <uc1_vc07> fuelLimitFailSafe :> validationCriteria {
                doc
                /* [VC#07] 페일세이프: 연료 분사를 공회전 수준 이하로 제한(L1) */
                msgFuelCutCmd.payload.injectionPulseWidth <= idleFuelPulseWidth
            }

            constraint postcondition {
                doc
                /* 오버라이드 후 공기/연료가 공회전 수준 이하로 제한되어 엔진은 유지되고 최종 토크가 최소화된 상태여야 함 */
                msgAirCutCmd.payload.massFlow <= idleAirMassFlow and
                msgFuelCutCmd.payload.injectionPulseWidth <= idleFuelPulseWidth
            }
        }

        // Interaction Flows

        // 1. Normal Scenario Flows
        flow from driver to UC1_Normal_Manual_Acceleration;
        flow from UC1_Normal_Manual_Acceleration to engine;
        flow from UC1_Normal_Manual_Acceleration to fuelSys;
        flow from fuelSys to UC1_Normal_Manual_Acceleration;
        flow from dynamicsSensor to UC1_Normal_Manual_Acceleration;

        // 2. Alternative Scenario Flows
        flow from ccLever to UC1_Alternative_Cruise_Control_Driving;
        flow from UC1_Alternative_Cruise_Control_Driving to engine;
        flow from UC1_Alternative_Cruise_Control_Driving to fuelSys;
        flow from fuelSys to UC1_Alternative_Cruise_Control_Driving;
        flow from dynamicsSensor to UC1_Alternative_Cruise_Control_Driving;

        // 3. Exception Scenario Flows
        flow from brake to UC1_Exception_Brake_Override_Intervention;
        flow from UC1_Exception_Brake_Override_Intervention to engine;
        flow from UC1_Exception_Brake_Override_Intervention to fuelSys;
        flow from powerSys to UC1_Alternative_Ignition_Off_Reset; // 점화 OFF 수신

        flow from driver to UC1_Alternative_Accel_Overrides_Cruise;
        flow from UC1_Alternative_Accel_Overrides_Cruise to engine;
        flow from addEcu to UC1_Exception_Brake_During_Intervention;
        flow from brake to UC1_Exception_Brake_During_Intervention;
        flow from UC1_Exception_Brake_During_Intervention to engine;
        flow from UC1_Exception_Brake_During_Intervention to fuelSys;
    }

    use case def <UC2> 'Emergency Intervention' {
        doc
        /* 빙판길 미끄럼 등 긴급 상황에서 ESP/TCU의 토크 저감 요청 시, 
         * 스로틀 공기량 제어와 연료/점화 지각 제어를 병렬로 수행하여 
         * 15ms 이내에 즉각적으로 물리적 토크를 저감하는 유스케이스
         */

        subject egas : EgasSystem;

        // 입력 액터
        actor addEcu : AddEcu; // ESP, TCU 등 외부 제어기

        // 출력 액터
        actor engine : Engine;
        actor fuelSys : FuelInjectionIgnitionSystem;

        satisfy requirement 'SHR-04-1'; // reqTorqueInterventionByAirflow
        satisfy requirement 'SHR-04-2'; // reqTorqueInterventionByFuelIgnition
        satisfy requirement 'SHR-04-3'; // reqTorqueInterventionFallbackFuelOnly (OR 대체 경로, UC2_Exception에서 실현)
        satisfy requirement 'SYSR-03';
        satisfy requirement 'SYSR-04';
        satisfy requirement 'SYSR-05';
        satisfy requirement 'SYSR-14';
        satisfy requirement 'SYSR-15';
        satisfy requirement 'SYSR-19';
        satisfy requirement 'SYSR-20';

        // ==========================================
        // 액션(시나리오) 정의 - 각 액션이 하나의 완전한 시나리오를 대변함
        // ==========================================

        action UC2_Normal_Emergency_Torque_Reduction {
            doc
            /* [주 성공 시나리오] 
             * ESP/TCU의 긴급 토크 저감 요청을 수신하여 15ms 이내에 목표 공기량을 축소함과 동시에, 
             * 연료 인젝션 펄스 단축 및 점화 시기를 지각시켜 신속하게 토크를 저감하는 전체 정상 제어 흐름
             */
            constraint precondition {
                doc
                /* ESP/TCU 등 외부 제어기에서 미끄럼 방지 등을 위한 토크 저감 요구(음수 값)를 전달한 상태여야 함 
                 * 수신 지연 15ms 이하의 정상 통신 상태여야 함
                 */
                egas.torqueInterventionPort.torqueReq.requestedTorqueDelta < 0.0 [N * m] and
                egas.torqueInterventionPort.torqueReq.messageAge <= commDelayThreshold
            }

            // [Messages]
            message msgInterventionReq of TorqueInterventionRequest
                from addEcu.requestsIntervention to egas.commandsEmergencyReduction {
                bind payload = egas.torqueInterventionPort.torqueReq;
            }

            message msgEmergAirCmd of IntakeAirFlow
                from egas.commandsEmergencyReduction to engine.receivesReducedAir {
                bind payload = egas.airIntakePort.airFlow;
                ref constraint <uc2_vc01>;
                ref constraint <uc2_vc02>;
            }

            message msgEmergFuelCmd of FuelIgnitionCommand
                from egas.commandsEmergencyReduction to fuelSys.executesReducedFuel {
                bind payload = egas.fuelCmdPort.fuelCmd;
                ref constraint <uc2_vc01>;
                ref constraint <uc2_vc03>;
            }

            // [Sequence Flow]
            first msgInterventionReq;

            // 토크 저감 요청 수신 후, 공기량 축소와 연료 분사 단축을 15ms 이내 병렬 하달
            fork commandOut;
                then msgEmergAirCmd;
                then msgEmergFuelCmd;

            // [Verification Criterias]
            constraint <uc2_vc01> emergencyResponseTime :> validationCriteria {
                doc
                /* [VC#01] 긴급 개입 응답 시간: 
                 * 토크 저감 요청 수신 후 15ms 이내에 공기량 및 연료 제어 명령이 병렬 하달되어야 함
                 */
                msgEmergAirCmd.start - msgInterventionReq.done <= interventionResponseBudget and
                msgEmergFuelCmd.start - msgInterventionReq.done <= interventionResponseBudget
            }

            constraint <uc2_vc02> airReductionConstraint :> validationCriteria {
                doc
                /* 공기량 즉각 축소: 직전 주기보다 물리적 공기량이 작아야 함 */
                msgEmergAirCmd.payload.massFlow < msgEmergAirCmd.payload.previousMassFlow
            }

            constraint <uc2_vc03> fuelReductionConstraint :> validationCriteria {
                doc
                /* 연료량 즉각 축소: 직전 주기보다 인젝션 펄스가 짧아야 함 */
                msgEmergFuelCmd.payload.injectionPulseWidth <
                msgEmergFuelCmd.payload.previousPulseWidth
            }

            constraint postcondition {
                doc
                /* 긴급 개입 종료 후 공기량과 연료량이 모두 직전 주기 대비 감소되어 토크가 저감된 상태여야 함 */
                msgEmergAirCmd.payload.massFlow < msgEmergAirCmd.payload.previousMassFlow and
                msgEmergFuelCmd.payload.injectionPulseWidth <
                msgEmergFuelCmd.payload.previousPulseWidth
            }
        }

        action UC2_Alternative_Communication_Delay_Compensation {
            doc
            /* [대안 시나리오] 
             * 외부 제어기와의 통신 지연으로 일시적인 토크 저감 신호 누락 발생 시, 
             * 타임아웃 전까지 직전의 유효한 토크 저감 요구값을 기반으로 자체 보상 제어를 유지하는 흐름
             * 수신 지연이 commDelayThreshold를 넘고 commTimeout 이내인 경우에만 동결하며, 
             * commTimeout을 넘으면 SYSR-05(UF2_4)가 개입을 무효화한다.
             */

            constraint precondition {
                doc
                /* 외부 제어기와의 통신 지연 또는 노이즈로 인해 토크 저감 요청 신호의 수신 지연이 15ms를 초과한 상태여야 함 */
                egas.torqueInterventionPort.torqueReq.messageAge > commDelayThreshold
            }

            // [Messages]
            message msgInterventionReq_Delay of TorqueInterventionRequest
                from addEcu.requestsIntervention to egas.compensatesCommDelay {
                bind payload = egas.torqueInterventionPort.torqueReq;
            }

            message msgMaintainAirCmd of IntakeAirFlow
                from egas.compensatesCommDelay to engine.receivesMaintainedAir {
                bind payload = egas.airIntakePort.airFlow;
                ref constraint <uc2_vc04>;
            }

            message msgMaintainFuelCmd of FuelIgnitionCommand
                from egas.compensatesCommDelay to fuelSys.executesMaintainedFuel {
                bind payload = egas.fuelCmdPort.fuelCmd;
                ref constraint <uc2_vc05>;
            }

            // [Sequence Flow]
            first msgInterventionReq_Delay;
            fork commandOut;
                then msgMaintainAirCmd;
                then msgMaintainFuelCmd;

            // [Verification Criterias]
            constraint <uc2_vc04> airMaintenanceConstraint :> validationCriteria {
                doc
                /* 공기량 동결: 통신 지연 시 직전 주기의 공기량을 그대로 유지 */
                msgMaintainAirCmd.payload.massFlow == msgMaintainAirCmd.payload.previousMassFlow
            }

            constraint <uc2_vc05> fuelMaintenanceConstraint :> validationCriteria {
                doc
                /* 연료량 동결: 통신 지연 시 직전 주기의 연료량을 그대로 유지 */
                msgMaintainFuelCmd.payload.injectionPulseWidth ==
                msgMaintainFuelCmd.payload.previousPulseWidth
            }

            constraint postcondition {
                doc
                /* 통신 지연 보상 종료 후 공기량과 연료량이 직전 주기 값과 동일하게 유지되어 급격한 토크 변화가 없는 상태여야 함 */
                msgMaintainAirCmd.payload.massFlow == msgMaintainAirCmd.payload.previousMassFlow and
                msgMaintainFuelCmd.payload.injectionPulseWidth ==
                msgMaintainFuelCmd.payload.previousPulseWidth
            }
        }

        action UC2_Alternative_Intervention_Release {
            doc
            /* [대안 시나리오]
             * 외부 제어기가 토크 저감 해제(requestedTorqueDelta >= 0)를 요청하면 긴급 개입 상태를 종료하고,
             * 공기/연료 명령을 운전자 요구 기반 제어로 복귀시키는 흐름 (스로틀 고착 래치가 없는 경우)
             */

            attribute releaseResponseLimit :> ISQ::duration; // [TBD] 섀시 제어 부서와 합의 후 값 입력

            constraint precondition {
                doc
                /* 긴급 개입이 활성 상태이며, 외부 제어기가 해제(토크 저감량 0 이상)를 요청한 상태여야 함 */
                egas.torqueInterventionPort.torqueReq.requestedTorqueDelta >= 0.0 [N * m]
            }

            // [Messages]
            message msgReleaseReq of TorqueInterventionRequest
                from addEcu.requestsIntervention to egas.releasesIntervention {
                bind payload = egas.torqueInterventionPort.torqueReq;
            }

            message msgResumedAirCmd of IntakeAirFlow
                from egas.releasesIntervention to engine.receivesDriverBasedAir {
                bind payload = egas.airIntakePort.airFlow;
                ref constraint <uc2_vc08>;
            }

            message msgResumedFuelCmd of FuelIgnitionCommand
                from egas.releasesIntervention to fuelSys.executesDriverBasedFuel {
                bind payload = egas.fuelCmdPort.fuelCmd;
                ref constraint <uc2_vc09>;
            }

            // [Sequence Flow]
            first msgReleaseReq;
            fork commandOut;
                then msgResumedAirCmd;
                then msgResumedFuelCmd;

            // [Verification Criterias] (EGAS 응답시간: 수신 → 출력 시각 차이)
            constraint <uc2_vc08> airResumeTimeConstraint :> validationCriteria {
                doc
                /* 해제 요청 수신 후 공기량 명령이 운전자 요구 기반으로 복귀하기까지의 EGAS 응답시간 */
                msgResumedAirCmd.start - msgReleaseReq.done <= releaseResponseLimit
            }

            constraint <uc2_vc09> fuelResumeTimeConstraint :> validationCriteria {
                doc
                /* 해제 요청 수신 후 연료/점화 명령이 운전자 요구 기반으로 복귀하기까지의 EGAS 응답시간 */
                msgResumedFuelCmd.start - msgReleaseReq.done <= releaseResponseLimit
            }

            constraint postcondition {
                doc
                /* 해제 후 긴급 개입이 종료되고 연료 차단 없이 운전자 요구 기반 제어로 복귀한 상태여야 함 */
                msgResumedAirCmd.start - msgReleaseReq.done <= releaseResponseLimit and
                msgResumedFuelCmd.start - msgReleaseReq.done <= releaseResponseLimit
            }
        }

        action UC2_Exception_Actuator_Stuck_Fuel_Cut {
            doc
            /* [예외 시나리오] 
             * 긴급 개입 중 스로틀 밸브 고착(Stuck) 등 하드웨어 오류로 공기량 축소가 불가능함이 감지될 경우, 
             * 즉시 공기량 제어 시도를 포기하고 엔진 보호를 위해 연료 시스템을 전면 차단(Fuel Cut)하는 흐름
             */
            constraint precondition {
                private import ThrottleStuckLogic::*;
                doc
                /* 긴급 개입 요청 중이며, 스로틀 목표/실제 개도 편차 초과가 확정 시간 이상 지속되어 고착이 확정된 상태여야 함 (IsThrottleStuck) */
                IsThrottleStuck(
                    egas.torqueInterventionPort.torqueReq.requestedTorqueDelta < 0.0 [N * m],
                    egas.throttle.positionCommand.openingPercentage,
                    egas.throttle.positionFeedback.openingPercentage,
                    stuckDeviationLimit,
                    egas.throttle.deviationDuration,
                    stuckConfirmTime
                )
            }

            // [Messages]
            message msgInterventionReq_Stuck of TorqueInterventionRequest
                from addEcu.requestsIntervention to egas.commandsEmergencyFuelCut {
                bind payload = egas.torqueInterventionPort.torqueReq;
            }

            message msgFuelCutCmd of FuelIgnitionCommand
                from egas.commandsEmergencyFuelCut to fuelSys.executesFuelCut {
                bind payload = egas.fuelCmdPort.fuelCmd;
                ref constraint <uc2_vc06>;
                ref constraint <uc2_vc07>;
            }

            // [Sequence Flow]
            first msgInterventionReq_Stuck;

            // 공기량 제어가 불가능하므로, 연료 시스템으로만 차단 명령을 즉시 하달
            then msgFuelCutCmd;

            // [Verification Criterias]
            constraint <uc2_vc06> stuckResponseTime :> validationCriteria {
                doc
                /* 고착 확정 후 연료 차단 명령까지 10ms 이내 (EGAS 응답시간: 확정 시점 → 출력 시작).
                 * 확정은 내부 이벤트라 메시지 시각 차이 대신 payload의 responseTime으로 판정한다.
                 */
                msgFuelCutCmd.payload.responseTime <= stuckCutResponseBudget
            }

            constraint <uc2_vc07> stuckFuelCutFailSafe :> validationCriteria {
                doc
                /* 페일세이프: 엔진 보호를 위한 연료 전면 차단 */
                msgFuelCutCmd.payload.injectionPulseWidth <= 0.0 [s]
            }

            constraint postcondition {
                doc
                /* 액추에이터 고착 대응 종료 후 연료 분사가 완전히 차단되어 토크가 안전 수준으로 저감된 상태여야 함 */
                msgFuelCutCmd.payload.injectionPulseWidth <= 0.0 [s]
            }
        }

        // ==========================================
        // 상호작용 및 시나리오 흐름(Flow) 정의
        // ==========================================

        // 1. 주 성공 시나리오(Normal)의 입출력 상호작용
        flow from addEcu to UC2_Normal_Emergency_Torque_Reduction;
        flow from UC2_Normal_Emergency_Torque_Reduction to engine;
        flow from UC2_Normal_Emergency_Torque_Reduction to fuelSys;

        // 2. 대안 시나리오(Alternative)의 입출력 상호작용
        flow from addEcu to UC2_Alternative_Communication_Delay_Compensation;
        flow from UC2_Alternative_Communication_Delay_Compensation to engine;
        flow from UC2_Alternative_Communication_Delay_Compensation to fuelSys;

        // 3. 예외 시나리오(Exception)의 입출력 상호작용 (스로틀 제어를 포기하므로 engine으로의 flow 생략)
        flow from addEcu to UC2_Exception_Actuator_Stuck_Fuel_Cut;
        flow from UC2_Exception_Actuator_Stuck_Fuel_Cut to fuelSys;
    }

    use case def <UC3> 'Hardware Fail-safe' {
        doc
        /* 이중화 센서 데이터를 실시간으로 모니터링하여 센서 결함과 과열 발생 시 즉각적인 페일세이프를 수행하고, 
         * 정상 작동 중에는 하드웨어 마찰 및 지연을 보정하여 실화를 방지하는 유스케이스
         */

        subject egas : EgasSystem;

        // 입력 액터
        actor sensors : AddSensorComponents;

        // 출력 및 피드백 액터
        actor engine : Engine;
        actor fuelSys : FuelInjectionIgnitionSystem;
        actor dashboard : DashboardHMI; // 출력 액터

        satisfy requirement 'SHR-03'; // reqFailSafeSensorMonitoring
        satisfy requirement 'SHR-02-2'; // reqMisfirePrevention
        satisfy requirement 'SHR-09'; // reqEngineOverheatProtection
        satisfy requirement 'SYSR-02';
        satisfy requirement 'SYSR-06';
        satisfy requirement 'SYSR-07';
        satisfy requirement 'SYSR-08';
        satisfy requirement 'SYSR-20';
        satisfy requirement 'SYSR-21';
        satisfy requirement 'SYSR-22';
        satisfy requirement 'SYSR-25'; // reqCriticalFaultDriverWarning

        // ==========================================
        // 액션(시나리오) 정의 - 각 액션이 하나의 완전한 시나리오를 대변함
        // ==========================================

        action UC3_Normal_Hardware_Delay_Compensation {
            doc
            /* [주 성공 시나리오] 
             * 양산 부품의 물리적 한계(마찰, 응답 지연 등)를 시스템이 실시간으로 자체 보정하여, 
             * 제어 명령 산출 후 액추에이터 지연을 10ms 이내로 통제하고 엔진 실화를 0Hz로 유지하는 전체 보정 제어 흐름
             */

            constraint precondition {
                doc
                /* 확정된 치명 고장이 없고, 구동 요구(가속 또는 크루즈)가 활성이며 
                 * 브레이크 오버라이드가 아닌 정상 주행 상태여야 함.
                 * 보정은 CF1이 산출한 기준 명령에 대한 후처리이다.
                 */
                egas.ecu.confirmedFaultCause == FaultCause::NoFault and
                SafeStateLogic::IsDrivingRequestActive(
                    egas.accelPort.accelIntent.pedalDisplacement,
                    egas.ecu.ccState
                ) and
                not SafeStateLogic::IsBrakeOverrideTriggered(
                    egas.accelPort.accelIntent.pedalDisplacement,
                    egas.ecu.ccState,
                    egas.brakePort.brakeInput.pressure
                )
            }

            // [Messages]
            message msgNormalData of EngineSensorData
                from sensors.sendsNormalSensorData to egas.compensatesDelayAndFriction {
                bind payload = egas.sensorPort.sensorData;
            }

            message msgCompensatedAirCmd of IntakeAirFlow
                from egas.compensatesDelayAndFriction to engine.receivesCompensatedAir {
                bind payload = egas.airIntakePort.airFlow;
            }

            message msgCompensatedFuelCmd of FuelIgnitionCommand
                from egas.compensatesDelayAndFriction to fuelSys.executesCompensatedFuel {
                bind payload = egas.fuelCmdPort.fuelCmd;
                ref constraint <uc3_vc1>;
            }

            message msgCombustionFeedback of CombustionSystemStatus
                from fuelSys.sendsCombustionFeedback to egas.compensatesDelayAndFriction {
                bind payload = egas.combustionStatusPort.combustionStatus;
                ref constraint <uc3_vc2>;
            }

            // [Sequence Flow]
            first msgNormalData;

            // 정상 센서 데이터 수신 후 보정된 공기/연료 제어 명령을 병렬 하달
            fork commandOut;
                then msgCompensatedAirCmd;
                then msgCompensatedFuelCmd;
                    first msgCompensatedAirCmd then j;
                    first msgCompensatedFuelCmd then j;

            // 명령 수행 후 실화율 등 연소 상태 피드백 수신
            join j;
            then msgCombustionFeedback;

            // [Verification Criterias]
            constraint <uc3_vc1> actuatorLatencyConstraint :> validationCriteria {
                doc
                /* [VC#15] 응답 시간(EGAS 소유): 정상 센서 데이터 수신 후 보정된 연료/점화 명령 출력 시작까지 10ms 이내 */
                msgCompensatedFuelCmd.start - msgNormalData.done <= compensationResponseBudget
            }

            constraint <uc3_vc2> misfirePreventionConstraint :> validationCriteria {
                doc
                /* [VC#16] 실화 방지: 
                 * 피드백되는 연소 상태에서 엔진 실화(Misfire Rate)가 완벽히 억제(0Hz)되어야 함
                 */
                @PlantObservation;
                msgCombustionFeedback.payload.misfireRate <= 0.0 [Hz]
            }

            constraint postcondition {
                doc
                /* 보정 제어 종료 후 액추에이터 응답 지연이 10ms 이내이고 엔진 실화가 발생하지 않은 상태로 유지되어야 함 */
                msgCompensatedFuelCmd.start - msgNormalData.done <= compensationResponseBudget and
                msgCombustionFeedback.payload.misfireRate <= 0.0 [Hz]
            }
        }

        action UC3_Exception_Critical_Sensor_Fault_FailSafe {
            doc
            /* [예외 시나리오]
             * 이중화 센서(PVS1/PVS2 또는 TPS1/TPS2)의 편차 초과가 확정 시간 이상 지속되어 치명 고장으로 확정되면,
             * 즉각 공기 유입을 차단하고 연료 제어를 전면 중단(L3)하는 페일세이프 흐름
             */
            constraint precondition {
                doc
                /* 가속 페달 또는 스로틀 센서의 편차가 확정되어 치명 고장 상태여야 함 */
                egas.ecu.confirmedFaultCause == FaultCause::PedalSensorDeviation or
                egas.ecu.confirmedFaultCause == FaultCause::ThrottleSensorDeviation
            }

            message msgAirCutCmd of IntakeAirFlow
                from egas.triggersEmergencyFailSafe to engine.receivesAirCut {
                bind payload = egas.airIntakePort.airFlow;
                ref constraint <uc3_vc3>;
                ref constraint <uc3_vc5>;
            }

            message msgFuelCutCmd of FuelIgnitionCommand
                from egas.triggersEmergencyFailSafe to fuelSys.executesFuelCut {
                bind payload = egas.fuelCmdPort.fuelCmd;
                ref constraint <uc3_vc4>;
                ref constraint <uc3_vc5>;
            }

            message msgDashboardWarning of DashboardWarning
                from egas.warnsCriticalFault to dashboard.displaysCriticalWarning {
                bind payload = egas.dashboardPort.dashboardWarning;
                ref constraint <uc3_vc9>; // 과열 시나리오는 <uc3_vc10>
            }

            // [Sequence Flow]
            first start;

            // 결함 센서 데이터 수신 즉시 스로틀 공기량 차단과 연료 분사 차단 명령을 병렬 하달
            fork commandOut;
                then msgAirCutCmd;
                then msgFuelCutCmd;
                then msgDashboardWarning; // 차단 명령과 병렬로 경고 출력

            // [Verification Criterias]
            constraint <uc3_vc3> sensorFaultAirCutConstraint :> validationCriteria {
                doc
                /* [VC#17] 페일세이프: 엔진 파손 및 급발진 방지를 위한 스로틀 공기 유입 원천 차단 */
                msgAirCutCmd.payload.massFlow <= 0.0 [kg / s]
            }

            constraint <uc3_vc4> sensorFaultFuelCutConstraint :> validationCriteria {
                doc
                /* [VC#18] 페일세이프: 시스템 보호를 위한 연료 분사 전면 차단 */
                msgFuelCutCmd.payload.injectionPulseWidth <= 0.0 [s]
            }
            constraint <uc3_vc5> failSafeResponseTime :> validationCriteria {
                doc
                /* [VC#19] 고장 확정 후 10ms 이내에 차단 명령이 병렬 하달되어야 함 (EGAS 응답시간) */
                msgAirCutCmd.payload.responseTime <= failSafeResponseBudget and
                msgFuelCutCmd.payload.responseTime <= failSafeResponseBudget
            }

            constraint <uc3_vc9> criticalWarningConstraint :> validationCriteria {
                doc
                /* [VC#9] 치명 고장 확정 시 운전자에게 치명 경고(Critical)가 표시되어야 함 */
                msgDashboardWarning.payload.status == DashboardWarningStatusEnum::Critical
            }

            constraint postcondition {
                doc
                /* 페일세이프 종료 후 공기 유입 및 연료 분사가 모두 차단되어 엔진이 안전 상태로 진입해 있어야 함 */
                msgAirCutCmd.payload.massFlow <= 0.0 [kg / s] and
                msgFuelCutCmd.payload.injectionPulseWidth <= 0.0 [s] and
                msgDashboardWarning.payload.status == DashboardWarningStatusEnum::Critical
            }
        }

        action UC3_Exception_Engine_Overheat_Protection {
            doc
            /* [예외 시나리오]
             * 엔진 냉각수 온도가 한계(120 °C)를 초과한 상태가 확정 시간 이상 지속되면, 엔진 파손을 막기 위해
             * 공기 유입을 차단하고 연료 제어를 전면 중단(L3)하는 열 보호 흐름
             */

            attribute overheatDuration :> ISQ::duration; // 과열 지속시간 관측값

            constraint precondition {
                private import SafeStateLogic::*;
                doc
                /* 냉각수 온도가 한계를 초과한 상태가 확정 시간 이상 지속된 상태여야 함 */
                IsOverheated(egas.sensorPort.sensorData.coolantTemp, coolantOverheatLimit) and
                overheatDuration >= overheatConfirmTime
            }

            message msgOverheatData of EngineSensorData
                from sensors.sendsFaultyData to egas.triggersEmergencyFailSafe {
                bind payload = egas.sensorPort.sensorData;
            }

            message msgAirCutCmd of IntakeAirFlow
                from egas.triggersEmergencyFailSafe to engine.receivesAirCut {
                bind payload = egas.airIntakePort.airFlow;
                ref constraint <uc3_vc6>;
                ref constraint <uc3_vc8>;
            }

            message msgFuelCutCmd of FuelIgnitionCommand
                from egas.triggersEmergencyFailSafe to fuelSys.executesFuelCut {
                bind payload = egas.fuelCmdPort.fuelCmd;
                ref constraint <uc3_vc7>;
                ref constraint <uc3_vc8>;
            }

            message msgDashboardWarning of DashboardWarning
                from egas.warnsCriticalFault to dashboard.displaysCriticalWarning {
                bind payload = egas.dashboardPort.dashboardWarning;
                ref constraint <uc3_vc9>; // 과열 시나리오는 <uc3_vc10>
            }

            first msgOverheatData;
            fork commandOut;
                then msgAirCutCmd;
                then msgFuelCutCmd;
                then msgDashboardWarning;

            constraint <uc3_vc6> overheatAirCutConstraint :> validationCriteria {
                doc
                /* 열 보호: 스로틀 공기 유입 차단 (L3) */
                msgAirCutCmd.payload.massFlow <= 0.0 [kg / s]
            }
            constraint <uc3_vc7> overheatFuelCutConstraint :> validationCriteria {
                doc
                /* 열 보호: 연료 분사 전면 차단 (L3) */
                msgFuelCutCmd.payload.injectionPulseWidth <= 0.0 [s]
            }
            constraint <uc3_vc8> overheatResponseTime :> validationCriteria {
                doc
                /* 과열 확정 시점의 센서 데이터 수신 후 10ms 이내에 차단 명령 하달 */
                msgAirCutCmd.start - msgOverheatData.done <= failSafeResponseBudget and
                msgFuelCutCmd.start - msgOverheatData.done <= failSafeResponseBudget
            }

            constraint <uc3_vc9> criticalWarningConstraint :> validationCriteria {
                doc
                /* [VC#9] 치명 고장 확정 시 운전자에게 치명 경고(Critical)가 표시되어야 함 */
                msgDashboardWarning.payload.status == DashboardWarningStatusEnum::Critical
            }
        }

        // ==========================================
        // 상호작용 및 시나리오 흐름(Flow) 정의
        // ==========================================

        // 1. 주 성공 시나리오(Normal)의 입출력 상호작용
        flow from sensors to UC3_Normal_Hardware_Delay_Compensation;
        flow from fuelSys to UC3_Normal_Hardware_Delay_Compensation; // 연소 상태(실화율) 및 액추에이터 응답 지연 피드백 수신
        flow from UC3_Normal_Hardware_Delay_Compensation to engine; // 보정 반영된 목표 공기량 전달
        flow from UC3_Normal_Hardware_Delay_Compensation to fuelSys; // 보정 반영된 연료/점화 명령 전달

        // 2. 예외 시나리오(Exception)의 입출력 상호작용
        flow from sensors to UC3_Exception_Critical_Sensor_Fault_FailSafe; // 결함 센서 데이터 감지
        flow from UC3_Exception_Critical_Sensor_Fault_FailSafe to engine; // 즉각적인 공기 유입 차단 명령 전달
        flow from UC3_Exception_Critical_Sensor_Fault_FailSafe to fuelSys; // 즉각적인 연료 차단(Fuel Cut) 명령 전달

        flow from UC3_Exception_Critical_Sensor_Fault_FailSafe to dashboard; // 치명 경고 전달
        flow from UC3_Exception_Engine_Overheat_Protection to dashboard;
    }

    use case def <UC4> 'Powertrain Calibration' {
        doc
        /* 엔진 성능 및 배출가스 최적화를 위해 외부 캘리브레이션 툴의 유효한 메모리 접근을 허가하고, 
         * 튜닝 데이터 업데이트 시 무결성을 검증하여 오염된 데이터로 인한 오작동을 차단하는 유스케이스
         */

        subject egas : EgasSystem;

        // 입출력 액터
        actor calTool : CalibrationTool; // 캘리브레이션 엔지니어 장비

        satisfy requirement 'SHR-05-1'; // reqCalibrationMemoryAccess
        satisfy requirement 'SHR-05-2'; // reqCalibrationDataIntegrity
        satisfy requirement 'SYSR-11';
        satisfy requirement 'SYSR-16';

        // ==========================================
        // 액션(시나리오) 정의 - 각 액션이 하나의 완전한 시나리오를 대변함
        // ==========================================

        action UC4_Normal_Memory_Access_Authorization {
            doc
            /* [주 성공 시나리오 1: 메모리 접근 인가] 
             * 캘리브레이션 툴이 유효한 메모리 주소로 맵 데이터 접근을 요청 시, 
             * 제어기가 정상 상태 코드(200)를 반환하여 통신 세션 및 접근을 허용하는 전체 흐름
             */
            constraint precondition {
                doc
                /* 인가된 읽기 요청: 유효 주소, 자격 일치, 점화 ON */
                egas.calibrationPort.calReq.operation == CalibrationOperationEnum::Read and
                DtcStroage::IsCalibrationAuthorized(
                    egas.calibrationPort.calReq.targetMemoryAddress,
                    egas.calibrationPort.calReq.accessCredential,
                    egas.ecu.expectedAccessCredential,
                    egas.calibrationPort.calReq.operation,
                    egas.ignitionPort.ignitionStatus.status,
                    egas.sensorPort.dynamicsStatus.vehicleSpeed
                )
            }

            // [Messages]
            message msgAccessReq of CalibrationRequest
                from calTool.requestsValidAccess to egas.authorizesAccess {
                bind payload = egas.calibrationPort.calReq;
            }

            message msgAccessRes of CalibrationStatus
                from egas.authorizesAccess to calTool.receivesAuthOk {
                bind payload = egas.calibrationPort.calStatus;
                ref constraint <uc4_vc1>;
                ref constraint <uc4_vc2>;
            }

            // [Sequence Flow]
            first msgAccessReq;

            // 캘리브레이션 툴의 접근 요청 수신 후 정상 상태 코드(200) 반환
            then msgAccessRes;

            // [Verification Criterias]
            constraint <uc4_vc1> accessAuthorizationSuccess :> validationCriteria {
                doc
                /* 인가 응답: 유효한 접근 요청에 대해 정상 상태 코드(200)를 반환 */
                msgAccessRes.payload.responseCode == 200
            }

            constraint <uc4_vc2> authResponseTime :> validationCriteria {
                doc
                /* 통신 응답 시간: 
                 * 메모리 접근 요청(msgAccessReq) 수신 후 50ms 이내에 인가 상태 코드(msgAccessRes)를 반환해야 함
                 */
                msgAccessRes.start - msgAccessReq.done <= accessAuthBudget
            }

            constraint postcondition {
                doc
                /* 접근 인가 절차 종료 후 통신 세션이 정상 상태 코드(200)로 개통되어 있어야 함 */
                msgAccessRes.payload.responseCode == 200
            }
        }

        action UC4_Normal_Data_Integrity_Verification {
            doc
            /* [주 성공 시나리오 2: 맵 데이터 무결성 검증] 
             * 파라미터 튜닝 데이터가 제어기에 기록된 직후, 시스템이 자체 검증 로직을 수행하여 
             * 유효한 메모리 체크섬을 툴로 반환하고 안전하게 업데이트를 확정하는 전체 흐름
             */
            constraint precondition {
                doc
                /* 인가된 쓰기 요청: 정차 중, 자격 일치, 점화 ON */
                egas.calibrationPort.calReq.operation == CalibrationOperationEnum::Write and
                DtcStroage::IsCalibrationAuthorized(
                    egas.calibrationPort.calReq.targetMemoryAddress,
                    egas.calibrationPort.calReq.accessCredential,
                    egas.ecu.expectedAccessCredential,
                    egas.calibrationPort.calReq.operation,
                    egas.ignitionPort.ignitionStatus.status,
                    egas.sensorPort.dynamicsStatus.vehicleSpeed
                )
            }

            // [Messages]
            message msgWriteDataReq of CalibrationRequest
                from calTool.sendsTuningData to egas.verifiesAndCommitsData {
                bind payload = egas.calibrationPort.calReq;
            }
            message msgChecksumRes of CalibrationStatus
                from egas.verifiesAndCommitsData to calTool.receivesVerifiedChecksum {
                bind payload = egas.calibrationPort.calStatus;
                ref constraint <uc4_vc3>;
                ref constraint <uc4_vc4>;
            }

            // [Sequence Flow]
            first msgWriteDataReq;

            // 튜닝 데이터 수신 및 자체 검증 완료 후 유효한 체크섬 반환
            then msgChecksumRes;

            // [Verification Criterias]
            constraint <uc4_vc3> dataIntegrityVerification :> validationCriteria {
                doc
                /* [uc4_vc3] EGAS가 계산한 체크섬이 요청 체크섬과 같고 롤백이 없어야 함 */
                msgChecksumRes.payload.verifiedChecksum ==
                msgWriteDataReq.payload.payloadChecksum and
                msgChecksumRes.payload.rolledBack == false
            }

            constraint <uc4_vc4> verificationResponseTime :> validationCriteria {
                doc
                /* 무결성 검증 응답 시간: 
                 * 데이터 기록 요청(msgWriteDataReq) 수신 후 검증 연산을 거쳐 100ms 이내에 체크섬(msgChecksumRes)을 반환해야 함
                 */
                msgChecksumRes.start - msgWriteDataReq.done <= mapUpdateBudget
            }

            constraint postcondition {
                doc
                /* 무결성 검증 절차 종료 후 갱신된 맵 데이터가 유효한 체크섬과 함께 커밋되어 있어야 함 */
                msgChecksumRes.payload.verifiedChecksum > 0
            }
        }

        action UC4_Exception_Invalid_Access_Or_Verification_Failure {
            doc
            /* [예외 시나리오] 
             * 유효하지 않은 메모리 주소로 접근하거나, 데이터 기록 후 체크섬 검증에 실패할 경우, 
             * 통신 에러 응답을 반환하고 업데이트된 데이터를 롤백하여 엔진 오작동을 차단하는 흐름
             */
            constraint precondition {
                doc
                /* 인가 조건(주소, 자격, 점화, 주행 중 쓰기)을 만족하지 못한 요청 */
                not DtcStroage::IsCalibrationAuthorized(
                    egas.calibrationPort.calReq.targetMemoryAddress,
                    egas.calibrationPort.calReq.accessCredential,
                    egas.ecu.expectedAccessCredential,
                    egas.calibrationPort.calReq.operation,
                    egas.ignitionPort.ignitionStatus.status,
                    egas.sensorPort.dynamicsStatus.vehicleSpeed
                )
            }

            // [Messages]
            message msgInvalidReq of CalibrationRequest
                from calTool.requestsInvalidAccess to egas.rejectsAndRollsBack {
                bind payload = egas.calibrationPort.calReq;
            }

            message msgErrorRes of CalibrationStatus
                from egas.rejectsAndRollsBack to calTool.receivesErrorResponse {
                bind payload = egas.calibrationPort.calStatus;
                ref constraint <uc4_vc5>;
                ref constraint <uc4_vc6>;
            }

            // [Sequence Flow]
            first msgInvalidReq;

            // 비유효한 요청 수신 즉시 에러 응답 및 기록 거부/롤백 처리
            then msgErrorRes;

            // [Verification Criterias]
            constraint <uc4_vc5> invalidAccessRejection :> validationCriteria {
                doc
                /* 예외 방어: 비정상적 접근이므로 상태 코드 200 이외의 에러 코드를 반환하여 데이터 기록을 차단 */
                msgErrorRes.payload.responseCode != 200
            }

            constraint <uc4_vc6> rejectionResponseTime :> validationCriteria {
                doc
                /* 보안/거절 응답 시간: 
                 * 잘못된 메모리 접근 요청에 대해 시스템 보호를 위해 10ms 이내에 즉각 통신을 거절해야 함
                 */
                msgErrorRes.start - msgInvalidReq.done <= addressRejectBudget
            }

            constraint postcondition {
                doc
                /* 오류 코드가 반환되고 메모리는 변경되지 않음 (롤백 대상 없음) */
                msgErrorRes.payload.responseCode != 200 and msgErrorRes.payload.rolledBack == false
            }

            action UC4_Exception_Verification_Failure_Rollback {
                doc
                /* [예외 시나리오] 인가된 쓰기에서 체크섬이 일치하지 않으면 오류 응답을 반환하고 쓰기를 취소하여 이전 값으로 복원하는 흐름 */
                constraint precondition {
                    doc
                    /* 인가된 쓰기 요청 */
                    egas.calibrationPort.calReq.operation == CalibrationOperationEnum::Write and
                    DtcStroage::IsCalibrationAuthorized(
                        egas.calibrationPort.calReq.targetMemoryAddress,
                        egas.calibrationPort.calReq.accessCredential,
                        egas.ecu.expectedAccessCredential,
                        egas.calibrationPort.calReq.operation,
                        egas.ignitionPort.ignitionStatus.status,
                        egas.sensorPort.dynamicsStatus.vehicleSpeed
                    )
                }
                message msgWriteReq of CalibrationRequest
                    from calTool.sendsTuningData to egas.verifiesAndCommitsData {
                    bind payload = egas.calibrationPort.calReq;
                }
                message msgErrorRes of CalibrationStatus
                    from egas.rejectsAndRollsBack to calTool.receivesErrorResponse {
                    bind payload = egas.calibrationPort.calStatus;
                    ref constraint <uc4_vc7>;
                    ref constraint <uc4_vc8>;
                }
                first msgWriteReq then msgErrorRes;

                constraint <uc4_vc7> rollbackOnMismatch :> validationCriteria {
                    doc
                    /* [uc4_vc7] 체크섬 불일치 시 오류 코드와 롤백 */
                    msgErrorRes.payload.verifiedChecksum != msgWriteReq.payload.payloadChecksum and
                    msgErrorRes.payload.responseCode != 200 and
                    msgErrorRes.payload.rolledBack == true
                }
                constraint <uc4_vc8> rollbackResponseTime :> validationCriteria {
                    doc
                    /* [uc4_vc8] 검증 후 오류 응답은 mapUpdateBudget 이내 */
                    msgErrorRes.start - msgWriteReq.done <= mapUpdateBudget
                }
                constraint postcondition {
                    doc
                    /* 메모리가 이전 값으로 복원된 상태 */
                    msgErrorRes.payload.rolledBack == true
                }
            }
        }

        // ==========================================
        // 상호작용 및 시나리오 흐름(Flow) 정의
        // ==========================================

        // 1. 주 성공 시나리오 1 (메모리 접근 인가)의 입출력 상호작용
        flow from calTool to UC4_Normal_Memory_Access_Authorization; // 메모리 접근 요청
        flow from UC4_Normal_Memory_Access_Authorization to calTool; // 200 응답 반환

        // 2. 주 성공 시나리오 2 (무결성 검증)의 입출력 상호작용
        flow from calTool to UC4_Normal_Data_Integrity_Verification; // 튜닝 데이터(mapDataPayload) 전송
        flow from UC4_Normal_Data_Integrity_Verification to calTool; // 검증된 체크섬 및 업데이트 완료 반환

        // 3. 예외 시나리오 (접근 거부 및 검증 실패)의 입출력 상호작용
        flow from calTool to UC4_Exception_Invalid_Access_Or_Verification_Failure;
        flow from UC4_Exception_Invalid_Access_Or_Verification_Failure to calTool; // 에러 코드 및 롤백 알림 반환
    }

    use case def <UC5> 'Diagnostics & Maintenance' {
        doc
        /* 시스템 결함 시 명확한 고장 진단 코드(DTC)를 제공하고, 
         * 부품 교체 후 용이한 영점 조정 프로세스를 지원하여 
         * A/S 정비사의 수리 시간 단축 및 유지보수 편의성을 보장하는 유스케이스
         */

        subject egas : EgasSystem;

        // 입출력 액터
        actor diagTool : DiagnosticTool; // 서비스 센터 A/S 정비사 진단기
        actor sensors : AddSensorComponents; // 물리적 결함 상태 제공(입력)

        satisfy requirement 'SHR-06'; // reqDiagnosticAndMaintenanceSupport
        satisfy requirement 'SYSR-09';
        satisfy requirement 'SYSR-17';

        // ==========================================
        // 액션(시나리오) 정의 - 각 액션이 하나의 완전한 시나리오를 대변함
        // ==========================================

        action UC5_Normal_Read_DTC_Scenario {
            doc
            /* [주 성공 시나리오 1: 고장 코드 조회] 
             * 냉각수 120도 초과 등 센서 결함 상태에서 진단기의 DTC 조회 요청(serviceId == 1) 수신 시, 
             * 제어기가 정상 응답(200)과 함께 유효한 고장 코드(DTC)를 즉시 반환하는 전체 진단 흐름
             */
            constraint precondition {
                doc
                /* 고장이 확정되어 비휘발성 메모리에 DTC가 기록된 상태(이전 주행 사이클 포함)에서 DTC 조회 요청이 수신됨 */
                egas.ecu.storedDtcCode > 0 and
                egas.diagPort.diagReq.serviceId == DtcStroage::diagServiceReadDtc // Before: serviceId == 1, 센서 결함 시뮬레이션
            }

            // [Messages]
            message msgDtcReq of DiagnosticRequest
                from diagTool.requestsDtcRead to egas.processesDtcRequest {
                bind payload = egas.diagPort.diagReq;
            }
            message msgDtcRes of DiagnosticStatus
                from egas.processesDtcRequest to diagTool.receivesDtcResponse {
                bind payload = egas.diagPort.diagStatus;
                ref constraint <uc5_vc1>;
                ref constraint <uc5_vc2>;
            }
            // [Sequence Flow]
            first msgDtcReq;

            // 결함이 기록된 상태에서 진단기의 DTC 조회 요청 수신 후 유효한 고장 코드 반환
            then msgDtcRes;

            // [Verification Criterias]
            constraint <uc5_vc1> dtcCodeConstraint :> validationCriteria {
                doc
                /* 저장된 DTC가 정상 응답과 함께 반환되어야 함 */
                msgDtcRes.payload.responseCode == 200 and
                msgDtcRes.payload.dtcCode == egas.ecu.storedDtcCode
            }

            constraint <uc5_vc2> dtcResponseTime :> validationCriteria {
                doc
                /* 진단 응답 시간: 진단기의 조회 요청 수신 후 50ms 이내에 DTC 응답을 반환해야 함 */
                msgDtcRes.start - msgDtcReq.done <= dtcResponseBudget
            }

            constraint postcondition {
                doc
                /* DTC 조회 종료 후 진단기에 유효한 고장 코드와 정상 응답이 전달되어 있어야 함 */
                msgDtcRes.payload.responseCode == 200 and msgDtcRes.payload.dtcCode > 0
            }
        }

        action UC5_Normal_Zero_Point_Calibration_Scenario {
            doc
            /* [주 성공 시나리오 2: 부품 영점 조정] 
             * 부품 교체 후 정비사가 진단기를 통해 영점 조정(serviceId == 2)을 요청 시, 
             * 제어기가 별도의 추가 프로그래밍 작업 없이 완료 응답(200)을 반환하여 수리 절차를 마무리하는 전체 흐름
             */
            constraint precondition {
                doc
                /* 영점 조정 루틴 요청(대상 센서 지정)이 점화 ON 정차 상태에서 수신됨 */
                egas.diagPort.diagReq.serviceId == DtcStroage::diagServiceRoutineControl and // Before: serviceId == 2
                DtcStroage::IsServiceModeAllowed(
                    egas.ignitionPort.ignitionStatus.status,
                    egas.sensorPort.dynamicsStatus.vehicleSpeed
                )
            }

            // [Messages]
            message msgZeroPointReq of DiagnosticRequest
                from diagTool.requestsZeroPointCal to egas.processesZeroPointCal {
                bind payload = egas.diagPort.diagReq;
            }
            message msgZeroPointRes of DiagnosticStatus
                from egas.processesZeroPointCal to diagTool.receivesZeroPointResponse {
                bind payload = egas.diagPort.diagStatus;
                ref constraint <uc5_vc3>;
                ref constraint <uc5_vc4>;
            }

            // [Sequence Flow]
            first msgZeroPointReq;

            // 영점 조정 요청 수신 후, 추가 개입 없이 성공 상태 코드(200) 반환
            then msgZeroPointRes;

            // [Verification Criterias]
            constraint <uc5_vc3> zeroPointCalibrationSuccess :> validationCriteria {
                doc
                /* 영점 조정 완료: 성공적인 영점 조정 후 정상 상태 코드(200) 반환 */
                msgZeroPointRes.payload.responseCode == 200
            }

            constraint <uc5_vc4> zeroPointResponseTime :> validationCriteria {
                doc
                /* 영점 조정 처리 시간: 영점 조정 요청 수신 후 보정 연산을 거쳐 100ms 이내에 완료 응답을 반환해야 함 */
                msgZeroPointRes.start - msgZeroPointReq.done <= zeroPointBudget
            }

            constraint postcondition {
                doc
                /* 영점 조정 종료 후 정상 완료 응답이 반환되어 신규 부품 기준값이 제어기에 반영되어 있어야 함 */
                msgZeroPointRes.payload.responseCode == 200
            }
        }

        action UC5_Alternative_Read_DTC_No_Fault {
            private import DtcStroage::*;
            doc
            /* [대안 시나리오] 저장된 DTC가 없을 때 DTC 조회는 정상 응답과 DTC 0(빈 목록)을 반환한다. */
            constraint precondition {
                doc
                /* 저장된 DTC가 없고 DTC 조회 요청이 수신됨 */
                egas.ecu.storedDtcCode == 0 and
                egas.diagPort.diagReq.serviceId == diagServiceReadDtc
            }
            message msgDtcReq of DiagnosticRequest
                from diagTool.requestsDtcRead to egas.processesDtcRequest {
                bind payload = egas.diagPort.diagReq;
            }
            message msgDtcRes of DiagnosticStatus
                from egas.processesDtcRequest to diagTool.receivesDtcResponse {
                bind payload = egas.diagPort.diagStatus;
                ref constraint <uc5_vc7>;
            }
            first msgDtcReq then msgDtcRes;
            constraint <uc5_vc7> emptyDtcResponse :> validationCriteria {
                doc
                /* [uc5_vc7] 무고장 시 정상 응답과 DTC 0, dtcResponseBudget 이내 */
                msgDtcRes.payload.responseCode == 200 and
                msgDtcRes.payload.dtcCode == 0 and
                msgDtcRes.start - msgDtcReq.done <= dtcResponseBudget
            }
            constraint postcondition {
                doc
                /* 빈 DTC 목록이 정상 응답으로 반환됨 */
                msgDtcRes.payload.dtcCode == 0
            }
        }

        action UC5_Exception_Invalid_Diagnostic_Request {
            private import DtcStroage::*;
            doc
            /* [예외 시나리오] 
             * 지원하지 않는 serviceId가 요청되거나, 물리적 결함이 없는데 DTC를 요구하는 등 유효하지 않은 요청 시, 
             * 에러 응답(Negative Response)을 반환하고 통신을 종료하는 흐름
             */
            constraint precondition {
                doc
                /* 미지원 서비스 요청, 또는 점화 OFF/주행 중의 영점 조정 요청 */
                (egas.diagPort.diagReq.serviceId != diagServiceReadDtc and
                    egas.diagPort.diagReq.serviceId != diagServiceRoutineControl) or
                (egas.diagPort.diagReq.serviceId == diagServiceRoutineControl and
                    not IsServiceModeAllowed(
                        egas.ignitionPort.ignitionStatus.status,
                        egas.sensorPort.dynamicsStatus.vehicleSpeed
                    ))
            }

            // [Messages]
            message msgInvalidReq of DiagnosticRequest
                from diagTool.requestsInvalidService to egas.rejectsInvalidRequest {
                bind payload = egas.diagPort.diagReq;
            }

            message msgErrorRes of DiagnosticStatus
                from egas.rejectsInvalidRequest to diagTool.receivesErrorResponse {
                bind payload = egas.diagPort.diagStatus;

                ref constraint <uc5_vc5>;
                ref constraint <uc5_vc6>;
            }

            // [Sequence Flow]
            first msgInvalidReq;

            // 미지원 서비스 ID 요청 시 에러 응답(Negative Response) 반환
            then msgErrorRes;

            // [Verification Criterias]
            constraint <uc5_vc5> invalidDiagnosticRequestRejection :> validationCriteria {
                doc
                /* 에러 응답: 처리할 수 없는 요청에 대해 에러 상태 코드를 반환하여 방어 (Negative Response) */
                msgErrorRes.payload.responseCode != 200
            }

            constraint <uc5_vc6> errorResponseTime :> validationCriteria {
                doc
                /* 거절 응답 시간: 잘못된 진단 서비스 요청에 대해 10ms 이내에 즉각 통신 거절 응답을 반환해야 함 */
                msgErrorRes.start - msgInvalidReq.done <= serviceRejectBudget
            }

            constraint postcondition {
                doc
                /* 예외 처리 종료 후 통신은 에러 응답으로 종료되고 진단/제어 상태는 변경되지 않아야 함 */
                msgErrorRes.payload.responseCode != 200
            }
        }

        // ==========================================
        // 상호작용 및 시나리오 흐름(Flow) 정의
        // ==========================================

        // 1. 주 성공 시나리오 1 (DTC 조회)의 입출력 상호작용
        flow from sensors to UC5_Normal_Read_DTC_Scenario; // 센서로부터 물리적 결함(온도 초과 등) 감지
        flow from diagTool to UC5_Normal_Read_DTC_Scenario; // 진단기의 DTC 읽기 요청 수신
        flow from UC5_Normal_Read_DTC_Scenario to diagTool; // 유효한 DTC 코드 및 200 응답 반환

        // 2. 주 성공 시나리오 2 (영점 조정)의 입출력 상호작용
        flow from diagTool to UC5_Normal_Zero_Point_Calibration_Scenario; // 진단기의 영점 조정 요청 수신
        flow from UC5_Normal_Zero_Point_Calibration_Scenario to diagTool; // 영점 조정 완료 및 200 응답 반환

        // 3. 예외 시나리오 (잘못된 요청)의 입출력 상호작용
        flow from diagTool to UC5_Exception_Invalid_Diagnostic_Request;
        flow from UC5_Exception_Invalid_Diagnostic_Request to diagTool; // 거부/에러 응답 반환
    }

    use case def <UC6> 'Architecture, Compliance & Reuse Review' {
        private import ScalarValues::*;
        doc
        /* UC1~UC5가 실시간 제어 상호작용(런타임 시나리오)을 다루는 것과 달리, 본 유스케이스는 신규 제어기 연동 시 아키텍처 확장성 검토,
         * ISO 26262 기능안전 인증 심사, 코어 로직 재사용률 분석이라는 비-런타임 검사(Inspection)/감사(Audit) 활동을 시나리오로 모델링한다.
         */

        subject egas : EgasSystem;

        actor platformEng : RV_StakeHolderModel::PlatformEngineer; // 아키텍처 확장성/재사용률 리뷰어
        actor regulator : RV_StakeHolderModel::SafetyRegulator; // ISO 26262 인증 심사 기관 대표

        satisfy requirement 'SHR-07'; // reqModularInterfaceArchitecture
        satisfy requirement 'SHR-P01'; // reqIso26262SafetyCompliance
        satisfy requirement 'SHR-P02'; // reqEfficientPlatformDevelopment
        satisfy requirement 'SYSR-12';

        action UC6_Normal_Architecture_Extensibility_Review {
            doc
            /* [검사 시나리오] 신규 외부 제어기(자율주행 ECU 등) 인터페이스 추가 시, 토크 중재 핵심 로직의 소스코드 변경 여부를 정적 분석/코드 리뷰로 확인 */

            attribute newInterfacePortAdded : Boolean; // 신규 외부 제어기 인터페이스 포트가 추가됨
            attribute coreLogicDiffLines : Natural; // 중재 핵심 로직의 변경 라인 수
            attribute pathBudgetCheckPassed : Boolean; // 경로 예산 검사(FV, M4) 통과 여부

            constraint precondition {
                doc
                /* 신규 외부 제어기 인터페이스가 추가되는 변경 요청이 접수된 상태 */
                newInterfacePortAdded == true
            }
            constraint postcondition {
                doc
                /* 중재 핵심 로직의 변경이 없고 경로 예산 검사가 계속 통과해야 함 (SYSR-12) */
                coreLogicDiffLines == 0 and pathBudgetCheckPassed == true
            }
        }

        action UC6_Normal_ASIL_D_Compliance_Audit {
            doc
            /* [감사 시나리오] 외부 공인 인증 기관이 ISO 26262 ASIL-D 산출물 및 개발 프로세스 준수 여부를 심사 */

            attribute asilDWorkProductsComplete : Boolean; // ASIL-D 산출물 준비 완료
            attribute auditOutcomeIssued : Boolean; // 인증서 또는 시정 조치 목록이 발행됨

            constraint precondition {
                doc
                /* ASIL-D 수준 산출물(안전 분석, 추적성, 검증 결과)이 감사 요청 시점에 준비된 상태 */
                asilDWorkProductsComplete == true
            }
            constraint postcondition {
                doc
                /* 감사 결과(인증서 또는 시정 조치 목록)가 발행되어야 함 */
                auditOutcomeIssued == true
            }
        }

        action UC6_Normal_Core_Logic_Reuse_Analysis {
            doc
            /* [분석 시나리오] 차기 파생 차종 개발 시 코어 로직(제어 알고리즘) 재사용률을 정적 분석 및 모델 리뷰로 측정 */

            attribute reuseRatePercent : Real; // 신규 차종 적용 시 핵심 로직 재사용률

            constraint precondition {
                doc
                /* 신규 차종 적용 분석이 요청되고 핵심 로직 기준선이 확정된 상태 */
                reuseRatePercent >= 0.0 and reuseRatePercent <= 100.0
            }
            constraint postcondition {
                doc
                /* 핵심 로직 재사용률이 목표 이상이어야 함 (SHR-P02) */
                reuseRatePercent >= coreLogicReuseTargetPct
            }
        }

        // ==========================================
        // 상호작용 및 시나리오 흐름(Flow) 정의
        // ==========================================
        flow from platformEng to UC6_Normal_Architecture_Extensibility_Review;
        flow from regulator to UC6_Normal_ASIL_D_Compliance_Audit;
        flow from platformEng to UC6_Normal_Core_Logic_Reuse_Analysis;
    } // package RV_UseCases
} // package RV_UseCases
