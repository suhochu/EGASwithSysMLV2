package RV_StakeholderReqValidationModel {
    private import RV_StakeholderRequirementModel::*;
    private import RV_InterfaceModel::*;
    private import VerificationCases::VerdictKind;
    private import VerificationCases::PassIf;
    private import SI::*;
    private import ScalarValues::*;
    private import ReqCommon::*;

    verification def ValidationOfStakeholderReq {
        subject context : RV_ContextModel::EgasContext; // 검증 대상을 EgasSystem 단일 요소가 아닌, 외부 액터가 포함된 전체 EgasContext로 지정
        attribute validationMethod : VVMethod;
    }

    verification def TestBrakeOverrideArbitration :> ValidationOfStakeholderReq {
        doc
        /* EgasContext 환경에서 운전자(Driver)가 가속 페달과 브레이크(Brake)를 동시에 조작하는 상충 상황을 모사하여,
         * 시스템이 제동 의도를 최우선으로 판단하고 토크(공기 유입량)를 강제 차단하는지 확인하는 실차 기반 인수 테스트
         */
        :>> validationMethod = VVMethod::Test;
        objective {
            verify stakeholderRequirementSet.reqSafeTorqueArbitration;
            assume constraint {
                context.egas.ecu.ccState == CruiseControlStateEnum::Off and
                context.egas.accelPort.accelIntent.pedalDisplacement == 50.0 [mm] and
                context.egas.brakePort.brakeInput.pressure == 1000.0 [Pa]
            }
        }
        // 테스트 사전 조건(Pre-condition) 모사: 두 페달이 동시에 밟힌 물리적 상황을 강제함
        return verdict : VerificationCases::VerdictKind = PassIf(
            SafeStateLogic::IsTorqueLimited(
                context.egas.airIntakePort.airFlow.massFlow,
                context.egas.fuelCmdPort.fuelCmd.injectionPulseWidth
            ) // 공기만 0 → L1
        );
        @MetaInformation {
            version = "v0.1";
        }
    }

    verification def TestBrakeOverrideOrderIndependence :> ValidationOfStakeholderReq {
        doc
        /* 가속과 제동이 모두 유지된 최종 입력 상태에서, 입력 순서와 무관하게 출력이 토크 제한(L1) 이내인지 확인한다.
         * 시험 절차(순서)는 아래 세 가지를 모두 수행하며 판정 기준은 같다.
         *  (1) 제동 입력 → 가속 입력   (2) 가속 입력 → 제동 입력   (3) 가속 입력 후 제동 → 제동 해제 없이 가속 재입력
         */
    }

    verification def TestPedalResponseAfterBrakeRelease :> ValidationOfStakeholderReq {
        doc
        /* 가속+제동 오버라이드 중 가속을 먼저 해제하고 제동을 해제한 뒤, 가속을 다시 입력했을 때 대기 상태에 갇히지 않고 정상 응답하는지 확인 */
        :>> validationMethod = VVMethod::Test;
        objective {
            verify stakeholderRequirementSet.reqSafeTorqueArbitration;
            assume constraint {
                context.egas.accelPort.accelIntent.pedalDisplacement == 50.0 [mm] and
                context.egas.brakePort.brakeInput.pressure == 0.0 [Pa]
            }
        }
        return verdict : VerdictKind = PassIf(
            context.egas.airIntakePort.airFlow.massFlow > SafeStateLogic::idleAirMassFlow // 오버라이드 해제 후 idle을 초과하는 정상 응답
        );
        @MetaInformation { version = "v0.1"; }
    }

    verification def DemonstrateSteadyStatePrecision :> ValidationOfStakeholderReq {
        private import TimingConceptsAndLimits::*;
        doc
        /* 동력계(Dynamometer) 환경에서 폐루프 제어의 정상 상태 오차 및 목표 토크 도달 시의 오버슈트 한계를 시연하는 검증 케이스 */
        :>> validationMethod = VVMethod::Demonstration;
        objective {
            // 분리된 정밀 제어 요구사항 매핑
            verify stakeholderRequirementSet.reqSteadyStatePrecision;
            assume constraint {
                SafeStateLogic::IsNormalDriving(
                    context.egas.accelPort.accelIntent.pedalDisplacement,
                    context.egas.ecu.ccState,
                    context.egas.brakePort.brakeInput.pressure,
                    context.egas.ecu.confirmedFaultCause,
                    context.egas.torqueInterventionPort.torqueReq.requestedTorqueDelta
                )
            }
        }
        // 폐루프 제어의 정상 상태 오차(2.0% 이하) 및 오버슈트(5.0% 이하) 판정
        return verdict : VerdictKind = PassIf(
            context.egas.combustionStatusPort.combustionStatus.steadyStateError <=
            torqueSteadyStateErrorLimitPct and
            context.egas.combustionStatusPort.combustionStatus.torqueOvershoot <=
            torqueOvershootLimitPct
        );
        @MetaInformation {
            version = "v0.2";
        }
    }
    verification def TestMisfirePrevention :> ValidationOfStakeholderReq {
        doc
        /* 가혹 조건의 실차 환경에서 하드웨어 지연 한계 내 응답성 및 엔진 실화(Misfire) 발생 여부를 측정하는 검증 케이스 */
        :>> validationMethod = VVMethod::Test;
        objective {
            verify stakeholderRequirementSet.reqMisfirePrevention;
        }
        // 실화 발생률(0Hz) 및 액추에이터 응답 지연(10ms 이하) 판정
        return verdict : VerdictKind = PassIf(
            context.egas.combustionStatusPort.combustionStatus.misfireRate <= 0.0 [Hz] and
            context.egas.fuelCmdPort.fuelCmd.responseTime <=
            TimingConceptsAndLimits::compensationResponseBudget
        );
        @MetaInformation {
            version = "v0.1";
        }
    }
    verification def TestPVSSensorFaultFailSafe :> ValidationOfStakeholderReq {
        doc
        /* HILS에서 PVS1/PVS2 편차를 한계 초과로 확정 시간 이상 주입하고, 
         * 안전 상태 L3(공기/연료 전면 차단) 진입을 확인하는 검증 케이스
         */
        :>> validationMethod = VVMethod::Test;
        objective {
            verify stakeholderRequirementSet.reqFailSafeSensorMonitoring;
            assume constraint {
                // 편차 10% > 한계 5%, sensorFaultConfirmTime 이상 유지 (지속시간은 시험 절차로 규정)
                context.egas.pedal.pedalPosition.pvs1Percentage == 50.0 and
                context.egas.pedal.pedalPosition.pvs2Percentage == 60.0
            }
        }
        return verdict : VerificationCases::VerdictKind = PassIf(
            context.egas.ecu.confirmedFaultCause == FaultCause::PedalSensorDeviation and
            SafeStateLogic::IsFullCutOff(
                context.egas.airIntakePort.airFlow.massFlow,
                context.egas.fuelCmdPort.fuelCmd.injectionPulseWidth
            )
        );
        @MetaInformation { version = "v0.2"; }
    }

    verification def TestTPSSensorFaultFailSafe :> ValidationOfStakeholderReq {
        doc
        /* HILS에서 TPS1/TPS2 편차를 한계 초과로 확정 시간 이상 주입하고, 
         * 안전 상태 L3(공기/연료 전면 차단) 진입을 확인하는 검증 케이스
         */
        :>> validationMethod = VVMethod::Test;
        objective {
            verify stakeholderRequirementSet.reqFailSafeSensorMonitoring;
            assume constraint {
                // 편차 10% > 한계 5%, sensorFaultConfirmTime 이상 유지 (지속시간은 시험 절차로 규정)
                context.egas.throttle.positionFeedback.tps1Percentage == 50.0 and
                context.egas.throttle.positionFeedback.tps2Percentage == 60.0
            }
        }
        return verdict : VerificationCases::VerdictKind = PassIf(
            context.egas.ecu.confirmedFaultCause == FaultCause::ThrottleSensorDeviation and
            SafeStateLogic::IsFullCutOff(
                context.egas.airIntakePort.airFlow.massFlow,
                context.egas.fuelCmdPort.fuelCmd.injectionPulseWidth
            )
        );
        @MetaInformation { version = "v0.1"; }
    }

    verification def TestInterventionViaAirflow :> ValidationOfStakeholderReq {
        doc
        /* 트랙 테스트 환경에서 ESP/TCU의 긴급 토크 저감 요청 시, 스로틀 밸브 제어(공기량 저감)의 15ms 이내 응답을 측정하는 검증 케이스 */
        :>> validationMethod = VVMethod::Test;
        objective {
            verify stakeholderRequirementSet.reqTorqueInterventionByAirflow; // SHR-04-1 검증
            assume constraint {
                context.egas.torqueInterventionPort.torqueReq.requestedTorqueDelta ==
                -100.0 [N * m] and
                context.egas.torqueInterventionPort.torqueReq.messageAge <=
                TimingConceptsAndLimits::commDelayThreshold
            }
        }
        return verdict : VerificationCases::VerdictKind = PassIf(
            context.egas.airIntakePort.airFlow.responseTime <=
            TimingConceptsAndLimits::interventionResponseBudget and
            context.egas.airIntakePort.airFlow.massFlow <
            context.egas.airIntakePort.airFlow.previousMassFlow
        );
        @MetaInformation { version = "v0.2"; }
    }
    verification def TestInterventionViaFuelIgnition :> ValidationOfStakeholderReq {
        doc
        /* 트랙 테스트 환경에서 ESP/TCU의 긴급 토크 저감 요청 시, 인젝터/점화 플러그 제어(연료량 저감)의 15ms 이내 응답을 측정하는 검증 케이스 */
        :>> validationMethod = VVMethod::Test;
        objective {
            verify stakeholderRequirementSet.reqTorqueInterventionByFuelIgnition; // SHR-04-2 검증
            assume constraint {
                context.egas.torqueInterventionPort.torqueReq.requestedTorqueDelta ==
                -100.0 [N * m] and
                context.egas.torqueInterventionPort.torqueReq.messageAge <=
                TimingConceptsAndLimits::commDelayThreshold
            }
        }
        return verdict : VerificationCases::VerdictKind = PassIf(
            context.egas.fuelCmdPort.fuelCmd.responseTime <=
            TimingConceptsAndLimits::interventionResponseBudget and
            context.egas.fuelCmdPort.fuelCmd.injectionPulseWidth <
            context.egas.fuelCmdPort.fuelCmd.previousPulseWidth
        );
        @MetaInformation { version = "v0.2"; }
    }

    verification def TestInterventionFallbackFuelOnly :> ValidationOfStakeholderReq {
        doc
        /* HILS에서 긴급 개입 중 TPS 값을 고정(고착)시켜 확정 시간 이후 연료 차단과 응답시간을 확인하는 검증 케이스 */
        :>> validationMethod = VVMethod::Test;
        objective {
            verify stakeholderRequirementSet.reqTorqueInterventionFallbackFuelOnly;
            assume constraint {
                context.egas.torqueInterventionPort.torqueReq.requestedTorqueDelta ==
                -100.0 [N * m] and
                context.egas.throttle.positionCommand.openingPercentage == 30.0 and
                context.egas.throttle.positionFeedback.openingPercentage == 80.0 and
                context.egas.throttle.deviationDuration >= ThrottleStuckLogic::stuckConfirmTime
            }
        }
        return verdict : VerdictKind = PassIf(
            context.egas.fuelCmdPort.fuelCmd.injectionPulseWidth <= 0.0 [s] and
            context.egas.fuelCmdPort.fuelCmd.responseTime <=
            TimingConceptsAndLimits::stuckCutResponseBudget
        );
        @MetaInformation { version = "v0.1"; }
    }

    verification def DemonstrateCalibrationAccessibility :> ValidationOfStakeholderReq {
        doc
        /* 엔진 벤치 테스트 환경에서 캘리브레이션 엔지니어가 표준 툴(예: XCP/CCP)을 연결하여 제어 맵(Map) 파라미터의 읽기/쓰기 접근 권한을 확인하고 튜닝이 실시간 반영되는지 시연하는 검증 케이스 */
        :>> validationMethod = VVMethod::Demonstration;
        // 검증 목표(objective)에 대상 요구사항을 명시하여 단방향 추적성 확보
        objective {
            verify stakeholderRequirementSet.reqPowertrainCalibrationSupport;
            // 통신 패킷 사전 조건 모사: 특정 주소(예: 40960)에 튜닝 값(1.05) 쓰기 요청
            assume constraint {
                context.egas.calibrationPort.calReq.targetMemoryAddress == 40960 and
                context.egas.calibrationPort.calReq.mapDataPayload == 1.05 and
                context.egas.calibrationPort.calReq.operation == CalibrationOperationEnum::Write and
                context.egas.calibrationPort.calReq.accessCredential ==
                context.egas.ecu.expectedAccessCredential and
                context.egas.ignitionPort.ignitionStatus.status == IgnitionStatusEnum::On and
                context.egas.sensorPort.dynamicsStatus.vehicleSpeed <=
                DtcStroage::serviceModeSpeedLimit
            }
        }
        // 제어기가 정상 응답 코드(200)를 반환하고, 유효한 체크섬(0보다 큰 값)이 발생했는지 판정
        return verdict : VerificationCases::VerdictKind = PassIf(
            context.egas.calibrationPort.calStatus.responseCode == 200 and
            context.egas.calibrationPort.calStatus.verifiedChecksum ==
            context.egas.calibrationPort.calReq.payloadChecksum and // Before: verifiedChecksum > 0
            context.egas.calibrationPort.calStatus.rolledBack == false
        );
        @MetaInformation {
            version = "v0.1";
        }
    }
    verification def DemonstrateDiagnosticAndZeroReset :> ValidationOfStakeholderReq {
        doc
        /* 서비스 센터(A/S) 환경을 모사하여, 진단기를 연결했을 때 고장 코드(DTC)가 정상 출력되고 부품 교체 후 영점 조정이 원활히 수행되는지 시연하는 검증 케이스 */
        :>> validationMethod = VVMethod::Demonstration;
        // 대상 요구사항을 명시하여 요구사항을 상향식으로 참조
        objective {
            verify stakeholderRequirementSet.reqDiagnosticAndMaintenanceSupport;
            // 확정된 치명 고장 상황에서 진단기가 DTC 읽기(serviceId == 1)를 요청한 통신 환경 주입
            assume constraint {
                context.egas.ecu.storedDtcCode > 0 and // S7: confirmedFaultCause → 저장 기록
                context.egas.diagPort.diagReq.serviceId == DtcStroage::diagServiceReadDtc
            }
        }
        // 제어기가 정상 응답 코드(200)와 함께 유효한 고장 코드(0 초과)를 반환하는지 판정
        return verdict : VerificationCases::VerdictKind = PassIf(
            context.egas.diagPort.diagStatus.responseCode == 200 and
            context.egas.diagPort.diagStatus.dtcCode > 0
        );
        @MetaInformation {
            version = "v0.1";
        }
    }

    verification def TestCalibrationAccessControl :> ValidationOfStakeholderReq {
        doc
        /* 점화 OFF, 주행 중 쓰기, 자격 불일치, 잘못된 주소를 각각 주입해 모두 오류 코드를 반환하는지 확인하는 검증 케이스 */
        :>> validationMethod = VVMethod::Test;
        objective {
            verify stakeholderRequirementSet.reqCalibrationMemoryAccess;
            assume constraint {
                context.egas.calibrationPort.calReq.operation == CalibrationOperationEnum::Write and
                context.egas.sensorPort.dynamicsStatus.vehicleSpeed >
                DtcStroage::serviceModeSpeedLimit // 주행 중 쓰기
            }
        }
        return verdict : VerdictKind = PassIf(
            context.egas.calibrationPort.calStatus.responseCode != 200
        );
        @MetaInformation { version = "v0.1"; }
    }

    verification def TestCalibrationWriteIntegrity :> ValidationOfStakeholderReq {
        doc
        /* 인가된 쓰기에서 체크섬이 일치하지 않는 데이터를 주입해 오류 코드와 롤백이 나오는지 확인하는 검증 케이스 */
        :>> validationMethod = VVMethod::Test;
        objective {
            verify stakeholderRequirementSet.reqCalibrationDataIntegrity;
            assume constraint {
                context.egas.calibrationPort.calReq.operation == CalibrationOperationEnum::Write and
                context.egas.calibrationPort.calReq.accessCredential ==
                context.egas.ecu.expectedAccessCredential and
                context.egas.ignitionPort.ignitionStatus.status == IgnitionStatusEnum::On and
                context.egas.sensorPort.dynamicsStatus.vehicleSpeed <=
                DtcStroage::serviceModeSpeedLimit and
                context.egas.calibrationPort.calStatus.verifiedChecksum !=
                context.egas.calibrationPort.calReq.payloadChecksum
            }
        }
        return verdict : VerdictKind = PassIf(
            context.egas.calibrationPort.calStatus.responseCode != 200 and
            context.egas.calibrationPort.calStatus.rolledBack == true
        );
        @MetaInformation { version = "v0.1"; }
    }

    verification def InspectModularArchitecture :> ValidationOfStakeholderReq {
        doc
        /* 도메인 전문가 및 소프트웨어 아키텍트가 참여하여 신규 외부 제어기(자율주행 ECU 등) 통합 시 코어 로직의 소스코드 변경 여부를 정적 분석 및 리뷰하는 검증 케이스 */
        // 검증 목표(objective)에 대상 요구사항을 명시하여 단방향 추적성 확보
        objective {
            verify stakeholderRequirementSet.reqModularInterfaceArchitecture;
        }
        :>> validationMethod = VVMethod::Inspection;
        // [개선 포인트] 리뷰어의 정성적 평가 결과를 검증 케이스 실행 시점의 입력(in)으로 받음
        attribute isCoreLogicModifiedByReview : Boolean;
        // 전문가가 코어 로직 수정이 없다고(false) 평가한 값을 입력하면 합격(Pass) 반환
        return verdict : VerificationCases::VerdictKind = PassIf(
            isCoreLogicModifiedByReview == false
        );
        @MetaInformation {
            version = "v0.1";
        }
    }
    verification def AuditIso26262AsilDCompliance :> ValidationOfStakeholderReq {
        doc
        /* 외부 공인 인증 기관의 감사를 통해 ISO 26262 ASIL-D 산출물 및 프로세스 준수 여부를 평가하는 검증 케이스 */
        // 프로젝트 요구사항이므로 특정 물리적 컨텍스트 대신 외부 감사 결과를 파라미터로 입력받음
        attribute isAsilDCertified : Boolean;
        :>> validationMethod = VVMethod::Inspection;
        // 검증 목표에 대상 요구사항 명시 (상향식 추적성)
        objective {
            verify stakeholderRequirementSet.reqIso26262SafetyCompliance;
        }
        // 감사 기관의 최종 통과 결과가 참(true)일 경우 합격(Pass) 반환
        return verdict : VerificationCases::VerdictKind = PassIf(isAsilDCertified == true);
        @MetaInformation {
            version = "v0.1";
        }
    }

    verification def AnalyzeCoreLogicReuseRate :> ValidationOfStakeholderReq {
        doc
        /* 소프트웨어 정적 분석 및 모델 리뷰를 통해 차기 파생 차종 개발 시 코어 로직의 재사용률(%)을 측정하는 검증 케이스 */
        // 실제 측정된 코드/모델 재사용률(%)을 파라미터로 입력받음
        attribute coreLogicReuseRate : Real;
        :>> validationMethod = VVMethod::Inspection;
        objective {
            verify stakeholderRequirementSet.reqEfficientPlatformDevelopment;
        }
        // 측정된 재사용률이 80.0% 이상일 경우에만 합격(Pass) 판정 반환
        return verdict : VerificationCases::VerdictKind = PassIf(coreLogicReuseRate >= 80.0);
        @MetaInformation {
            version = "v0.1";
        }
    }

    verification def TestDriverPedalResponsiveness :> ValidationOfStakeholderReq {
        doc
        /* 실차 주행 시험에서 가속 페달 입력 후 EGAS의 명령 출력 시간과 차량 종방향 Jerk를 함께 계측하는 검증 케이스 */
        :>> validationMethod = VVMethod::Test;
        objective {
            verify stakeholderRequirementSet.reqDriverPedalResponsiveness;
            verify requirement 'SYSR-26';
            assume constraint {
                context.egas.accelPort.accelIntent.pedalDisplacement == 50.0 [mm] and
                SafeStateLogic::IsNormalDriving( // [R5] Jerk 판정은 정상 주행에서만
                    context.egas.accelPort.accelIntent.pedalDisplacement,
                    context.egas.ecu.ccState,
                    context.egas.brakePort.brakeInput.pressure,
                    context.egas.ecu.confirmedFaultCause,
                    context.egas.torqueInterventionPort.torqueReq.requestedTorqueDelta
                )
            }
        }
        return verdict : VerdictKind = PassIf(
            context.egas.airIntakePort.airFlow.responseTime <=
            TimingConceptsAndLimits::pedalResponseBudget and
            context.egas.fuelCmdPort.fuelCmd.responseTime <=
            TimingConceptsAndLimits::pedalResponseBudget and
            context.egas.sensorPort.dynamicsStatus.longitudinalJerk <= 10.0 // 플랜트 관측: 판정에만 사용
        );
        @MetaInformation { version = "v0.1"; }
    }

    verification def TestEngineOverheatProtection :> ValidationOfStakeholderReq {
        doc
        /* HILS에서 냉각수 온도를 한계 초과로 확정 시간 이상 주입하고, 과열 확정과 L3 진입을 확인하는 검증 케이스 */
        :>> validationMethod = VVMethod::Test;
        objective {
            verify stakeholderRequirementSet.reqEngineOverheatProtection;
            assume constraint {
                context.egas.sensorPort.sensorData.coolantTemp == 403.15 [K] // 130 °C
            }
        }
        return verdict : VerdictKind = PassIf(
            context.egas.ecu.confirmedFaultCause == FaultCause::Overheat and
            SafeStateLogic::IsFullCutOff(
                context.egas.airIntakePort.airFlow.massFlow,
                context.egas.fuelCmdPort.fuelCmd.injectionPulseWidth
            )
        );
        @MetaInformation { version = "v0.1"; }
    }

    verification def TestCruiseSpeedHold :> ValidationOfStakeholderReq {
        doc
        /* 동력계/HILS 평지 조건에서 크루즈를 설정하고, 정상 상태에서 설정 속도 대비 속도 오차율이 한계 이내인지 확인하는 검증 케이스 */
        :>> validationMethod = VVMethod::Test;
        objective {
            verify stakeholderRequirementSet.reqCruiseSpeedHold;
            assume constraint {
                context.egas.ecu.ccState == CruiseControlStateEnum::Active and
                context.egas.ecu.ccSetSpeed == 80.0 [km / h] // 예시 설정 속도
            }
        }
        return verdict : VerdictKind = PassIf(
            CruiseControlLogic::IsCruiseSpeedHeld(
                context.egas.ecu.ccSetSpeed,
                context.egas.sensorPort.dynamicsStatus.vehicleSpeed,
                CruiseControlLogic::cruiseSpeedErrorLimitPct
            )
        );
        @MetaInformation { version = "v0.1"; }
    }
} // package RV_StakeholderReqValidationModel
