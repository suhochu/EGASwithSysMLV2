package EgasSystemContext {
    doc
    /* [시스템 컨텍스트 뷰포인트]
     * EGAS(관심 시스템)의 경계를 정의하는 어휘를 제공한다: 외부 액터, 주고받는 아이템(payload), 경계 포트,
     * 그리고 관심 시스템 자체(EgasSystem)를 블랙박스로, 시스템+외부 액터 전체를 컨텍스트(EgasContext)로 정의한다.
     * 내부 컴포넌트(EngineControlUnit/AccelerationPedal/ThrottleValve)는 05/06번 파일에서 그레이박스 유스케이스의
     * subject나 요구사항의 allocationBudget 대상으로 참조되지만, 이 파일의 EgasSystem 정의 자체는 포트만 노출하는
     * 순수 블랙박스이며 내부 배선(어떻게 연결되는지)은 "02. Functional Viewpoint"가 책임진다.
     */

    private import ReqCommon::*;
    private import ScalarValues::*;

    @MetaInformation {
        version = "v0.1";
    }

    // ==========================================
    // 1. 내부 컴포넌트 정의 (Internal Components)
    // - 관심 시스템 내부의 요소로, 그레이박스 유스케이스(05번 파일)와 요구사항 할당(06번 파일)의 대상이 됨
    // ==========================================

    part def EngineControlUnit {
        doc
        /* 시스템의 중앙 마이크로컨트롤러(µC)로서 가속 페달, 크루즈 컨트롤, 외부 제어기의 토크 요구(Torque Request)를 수집 및 중재(Arbitration)함.
         * 목표 토크를 달성하기 위해 스로틀 밸브 및 연료/점화 시스템에 제어 명령을 내리며, 오작동을 감지하는 안전 모니터링을 수행함.
         */
    }

    part def AccelerationPedal {
        doc
        /* 운전자의 물리적인 가속 의지(페달을 밟는 정도)를 전기적 신호로 변환하여 ECU에 1차적인 운전자 토크 요구량으로 전달함. */
    }

    part def ThrottleValve {
        doc
        /* ECU의 제어 명령에 따라 개방 각도를 조절하여 엔진으로 유입되는 공기량을 물리적으로 제어함. 
         * 동시에 현재 밸브의 위치 값을 ECU로 피드백하여 정밀한 폐루프 제어(Closed-loop control)를 가능하게 함.
         */
    }

    // ==========================================
    // 2. 외부 액터 정의 (External Actors)
    // ==========================================

    part def Driver {
        doc
        /* 가속 페달을 밟아 가속 의도를 표현하는 물리적 운전자. AccelerationPedal(센서)이 EgasSystem
         * 내부 컴포넌트로 포함되므로, 운전자의 물리적 가속 의도가 시스템 경계를 넘는 입력이 된다.
         * (03번 파일의 stakeholder Driver와는 별개 개념: 이해관계자 관점이 아닌 컨텍스트 경계 관점의 액터)
         */
    }

    part def CruiseControlLever {
        doc
        /* 크루즈 컨트롤(Cruise Control) 활성화를 위한 운전자의 조작 상태를 전달하며, 지정된 속도를 유지하기 위한 지속적인 토크 요구 명령을 시스템에 입력함. */
    }

    part def Brake {
        doc
        /* 운전자의 제동 의지를 ECU에 전달함. 
         * 가속 페달 신호와 브레이크 신호가 동시에 입력될 경우, 제동을 우선시하여 토크를 강제로 차단하거나 줄이는 안전 기능(Brake Override)을 트리거함.
         */
    }

    part def AddEcu {
        doc
        /* 변속기 제어기(TCU), 차체 자세 제어기(ESP) 등 다른 시스템의 마이크로컨트롤러가 전송하는 토크 개입(Torque Intervention) 신호를 전달함. 
         * 기어 변속 시점의 토크 저감이나 미끄럼 방지를 위한 토크 제한 등을 요구함.
         */
    }

    part def AddSensorComponents {
        doc
        /* 엔진 회전수(RPM), 냉각수 온도, 흡기 온도 등 ECU가 목표 토크를 정확하게 계산하고 보정하는 데 필요한 주변 환경 및 물리적 상태 데이터를 제공함. */
    }

    part def FuelInjectionIgnitionSystem {
        doc
        /* 스로틀 밸브의 공기량 제어와 협조하여, ECU가 요구하는 최종 토크를 실제 엔진 동력으로 구현하기 위해 연료 분사량과 점화 시기를 제어하는 외부 구동계 역할을 수행함. */
    }

    part def Engine {
        doc
        /* 스로틀 밸브(ThrottleValve)를 통해 유입된 공기를 받아들이는 물리적 엔진 블록(실린더/흡기 매니폴드).
         * FuelInjectionIgnitionSystem과는 별도의 외부 액터로, 공기 경로(air path)만을 담당함.
         */
    }

    part def CalibrationTool {
        doc
        /* 엔지니어가 사용하는 외부 XCP/CCP 튜닝 장비 */
    }

    // ==========================================
    // 3. 페이로드 (Item) 정의
    // ==========================================

    item def CruiseControlCommand {
        doc
        /* 설정 속도, 크루즈 컨트롤 On/Off/Cancel 상태 등 */
        @MetaInformation {
            version = "v0.2";
        }
    }
    item def BrakePedalPosition {
        doc
        /* 브레이크 페달이 밟힌 물리적 깊이 또는 압력 센서 값 */
        attribute pressure :> ISQ::pressure;
        @MetaInformation {
            version = "v0.3";
        }
    }
    item def TorqueInterventionRequest {
        doc
        /* TCU나 ESP 등 외부 제어기가 요구하는 토크 증감 요구량 */
        attribute latency :> ISQ::duration;
        attribute requestedTorqueDelta :> ISQ::torque;
        @MetaInformation {
            version = "v0.3";
        }
    }
    item def EngineSensorData {
        doc
        /* RPM, 냉각수 온도, 흡기 온도, 산소 센서 값 등 엔진 제어에 필요한 복합 데이터 */
        attribute engineRpm :> ISQ::frequency;
        attribute coolantTemp :> ISQ::thermodynamicTemperature;
        @MetaInformation {
            version = "v0.3";
        }
    }

    item def AccelerationPedalPosition {
        doc
        /* [내부용] AccelerationPedal 센서가 생성하여 ECU로 전달하는 이중화 전기 신호(PVS1/PVS2). Driver의 AccelerationIntent를
         * 내부적으로 변환한 결과이며, 시스템 경계를 넘나들지 않는다.
         */
        @MetaInformation {
            version = "v0.2";
        }
    }
    item def ThrottlePositionCommand {
        doc
        /* ECU가 스로틀 밸브 모터에 내리는 목표 개도각(Angle) 제어 신호 */
        @MetaInformation {
            version = "v0.2";
        }
    }
    item def ThrottlePositionFeedback {
        doc
        /* 스로틀 밸브의 현재 위치 센서(TPS) 피드백 값 */
        @MetaInformation {
            version = "v0.2";
        }
    }

    item def FuelIgnitionCommand {
        doc
        /* 인젝터 분사 시간(Pulse Width) 및 점화 플러그 점화 시기(Timing) 신호 */
        attribute injectionPulseWidth :> ISQ::duration;
        @MetaInformation {
            version = "v0.3";
        }
    }
    item def CombustionSystemStatus {
        doc
        /* 연료/점화 구동계의 작동 상태 및 고장 진단(OBD) 피드백 */
        attribute misfireRate :> ISQ::frequency;
        attribute steadyStateError : Real;
        attribute actualTorqueValue :> ISQ::torque;
        @MetaInformation {
            version = "v0.3";
        }
    }

    item def AccelerationIntent {
        doc
        /* [경계 입력] 운전자가 가속 페달을 밟는 물리적 정도/변위 (0~100%). EgasSystem 내부의 AccelerationPedal
         * 컴포넌트가 이 값을 수신하여 이중화 전기 신호(AccelerationPedalPosition)로 변환함.
         */
        attribute pedalDisplacement :> ISQ::length;
        @MetaInformation {
            version = "v0.3";
        }
    }
    item def IntakeAirFlow {
        doc
        /* [경계 출력] 스로틀 밸브의 개도각에 따라 엔진(Engine)으로 유입되는 공기 질량 유량(Air Mass Flow). */
        attribute massFlow :> ISQ::massFlowRate;
        @MetaInformation {
            version = "v0.2";
        }
    }

    item def CalibrationRequest {
        doc
        /* 캘리브레이션 툴에서 전송하는 맵 데이터 메모리 주소 및 튜닝 데이터 페이로드 */

        attribute targetMemoryAddress : Integer; // 접근하려는 제어기 내부 메모리 번지수
        attribute mapDataPayload : Real; // 쓰기/업데이트할 엔진 맵 파라미터 값

        @MetaInformation {
            version = "v0.3";
        }
    }

    item def CalibrationStatus {
        doc
        /* ECU가 반환하는 통신 응답 코드 및 업데이트된 맵 데이터의 무결성 검증 값 */

        attribute responseCode : Integer; // 예: 200(OK/접근 허용), 401(Locked) 등 통신 상태 코드
        attribute verifiedChecksum : Integer; // 맵 데이터 업데이트 후 확인된 메모리 체크섬 값

        @MetaInformation {
            version = "v0.3";
        }
    }

    item def DiagnosticRequest {
        doc
        /* 진단기(OBD 스캐너 등)에서 UDS(Unified Diagnostic Services) 프로토콜 기반으로 전송하는 진단 서비스 요청 패킷 */

        attribute serviceId : Integer; // 예: 1(ReadDTC - DTC 읽기), 2(RoutineControl - 영점 조정)
        attribute dataRecord : Integer; // 진단 세부 명령 또는 루틴 식별자(ID) 페이로드

        @MetaInformation {
            version = "v0.3";
        }
    }

    item def DiagnosticStatus {
        doc
        /* ECU가 진단기로 반환하는 응답 상태 및 실제 DTC 데이터 페이로드 */

        attribute responseCode : Integer; // 예: 200(Positive Response / 정상 수행), 400(Negative Response)
        attribute dtcCode : Integer; // 출력된 실제 고장 코드 값 (고장이 없을 경우 0)

        @MetaInformation {
            version = "v0.3";
        }
    }

    // ==========================================
    // 4. 포트 정의 (Port Definitions)
    // - EgasSystem 경계에서 주고받는 아이템의 방향(in/out)을 명시함
    // ==========================================

    port def CruiseControlPort {
        in ccCmd : CruiseControlCommand;
        @MetaInformation {
            version = "v0.2";
        }
    }
    port def BrakeInputPort {
        in brakeInput : BrakePedalPosition;
        @MetaInformation {
            version = "v0.2";
        }
    }
    port def TorqueInterventionPort {
        in torqueReq : TorqueInterventionRequest;
        @MetaInformation {
            version = "v0.2";
        }
    }
    port def SensorInputPort {
        in sensorData : EngineSensorData;
        @MetaInformation {
            version = "v0.2";
        }
    }
    port def FuelCommandPort {
        out fuelCmd : FuelIgnitionCommand;
        @MetaInformation {
            version = "v0.2";
        }
    }
    port def CombustionStatusPort {
        in combustionStatus : CombustionSystemStatus;
        @MetaInformation {
            version = "v0.2";
        }
    }
    port def AccelerationInputPort {
        in accelIntent : AccelerationIntent;
        @MetaInformation {
            version = "v0.2";
        }
    }
    port def AirIntakePort {
        out airFlow : IntakeAirFlow;
        @MetaInformation {
            version = "v0.2";
        }
    }

    port def CalibrationPort {
        doc
        /* 캘리브레이션 툴과 연결되는 양방향 통신 포트 */
        in calReq : CalibrationRequest;
        out calStatus : CalibrationStatus;
        @MetaInformation {
            version = "v0.2";
        }
    }
    part def DiagnosticTool {
        doc
        /* 서비스 센터(A/S) 엔지니어가 사용하는 외부 진단 장비 */
        @MetaInformation {
            version = "v0.2";
        }
    }

    port def DiagnosticPort {
        doc
        /* 진단기(DiagnosticTool)와 연결되는 양방향 통신 포트 */
        in diagReq : DiagnosticRequest;
        out diagStatus : DiagnosticStatus;
        @MetaInformation {
            version = "v0.2";
        }
    }

    // ==========================================
    // 5. 관심 시스템 (System of Interest) 정의
    // - 요구사항 뷰포인트에서는 블랙박스로만 취급: 포트(인터페이스)만 노출하고
    //   내부 구성(컴포넌트 분해 및 내부 흐름)은 기능/논리 뷰포인트에서 정의함
    // ==========================================

    part def EgasSystem {
        port ccPort : CruiseControlPort;
        port brakePort : BrakeInputPort;
        port torqueInterventionPort : TorqueInterventionPort;
        port sensorPort : SensorInputPort;
        port fuelCmdPort : FuelCommandPort;
        port combustionStatusPort : CombustionStatusPort;
        port accelPort : AccelerationInputPort;
        port airIntakePort : AirIntakePort;
        port calibrationPort : CalibrationPort;
        port diagPort : DiagnosticPort;

        @MetaInformation {
            version = "v0.2";
        }
    }

    // ==========================================
    // 6. 시스템 컨텍스트 (System Context)
    // ==========================================

    part def EgasContext {
        // 외부 환경(액터) 인스턴스화
        part driver : Driver;
        part ccLever : CruiseControlLever [0..1];
        part brake : Brake;
        part addEcu : AddEcu;
        part sensors : AddSensorComponents;
        part fuelSys : FuelInjectionIgnitionSystem;
        part engine : Engine;
        part calTool : CalibrationTool;
        part diagTool : DiagnosticTool;

        // 관심 시스템 전체를 하나의 파트로 인스턴스화
        part egas : EgasSystem;

        // 외부 액터와 시스템 경계 포트 간의 흐름 (내부 파트에는 직접 접근하지 않음)
        flow of AccelerationIntent from driver to egas.accelPort.accelIntent;
        flow of CruiseControlCommand from ccLever to egas.ccPort.ccCmd;
        flow of BrakePedalPosition from brake to egas.brakePort.brakeInput;
        flow of TorqueInterventionRequest from addEcu to egas.torqueInterventionPort.torqueReq;
        flow of EngineSensorData from sensors to egas.sensorPort.sensorData;

        // 연료/점화 시스템과의 양방향 제어 및 피드백 흐름
        flow of FuelIgnitionCommand from egas.fuelCmdPort.fuelCmd to fuelSys;
        flow of CombustionSystemStatus from fuelSys to egas.combustionStatusPort.combustionStatus;

        // 스로틀 밸브(내부)가 만들어낸 공기 흐름이 엔진으로 전달됨
        flow of IntakeAirFlow from egas.airIntakePort.airFlow to engine;

        // Calibariont Tool 과의 양방향 데이터 전달 및 입력
        flow of CalibrationRequest from calTool to egas.calibrationPort.calReq;
        flow of CalibrationStatus from egas.calibrationPort.calStatus to calTool;

        // 진단기와 EgasSystem 간의 양방향 데이터 흐름(Flow) 연결
        flow of DiagnosticRequest from diagTool to egas.diagPort.diagReq;
        flow of DiagnosticStatus from egas.diagPort.diagStatus to diagTool;

        @MetaInformation {
            version = "v0.2";
        }
    } // package EgasSystemContext
} // package EgasSystemContext
