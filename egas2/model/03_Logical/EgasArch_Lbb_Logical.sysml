package EgasArch_Lbb_Logical {
    private import EgasArch_Ctx_Context::EgasSystem;

    part def LogicalEgasSystem :> EgasSystem {
        doc
        /* Logical black box. It adopts the boundary of the functional black box and inherits its ports from EgasSystem. */
    }
} // package EgasArch_Lbb_Logical
